Dim storePath as String

' Sub to read the Store Path
Function ReadSPath()
  os = UCase(Left(CATIA.SystemConfiguration.OperatingSystem, 3))
  sep = "/"
  If (os = "WIN") Or (os = "INT") Then
    sep = "\"
  End If

  If (Len(storePath) = 0) Then
    ret = InputBox("Enter Path for CATPart or CATProduct (e.g. c:" + sep + "catfiles" + sep + ")", "Save as")
    storePath = ret
  End If

  Set fso = CreateObject("Scripting.FileSystemObject")

  If (Len(storePath) = 0) Or (fso.FolderExists(storePath) = False) Then
    Set fso = Nothing
    ReadSPath = Empty
    Exit Function
  End If

  If (Mid(storePath, Len(storePath), 1) <> sep) Then
    storePath = storePath + sep
  End If

  ReadSPath = storePath
  Set fso = Nothing
End Function

' Sub to store a document'
Sub SaveDocument(document, name)
  document.SaveAs storePath & name
End Sub

' Sub to retrieve a name in capital letters'
Function GetUCaseName(name)
  ucaseName = Left(name, InStrRev(name, ".") - 1)
  extension = Right(name, Len(name) - InStr(name, ".") + 1)
  GetUCaseName = UCase(ucaseName) + extension
End Function

Function toolCall0(wpart,HybridBody1)
  wPart.InWorkObject = HybridBody1
  wPart.Update

  Set hypFact = wPart.HybridShapeFactory
  Set HybridShapePointCoord0 = hypFact.AddNewPointCoord(0, 0, 0)
  HybridBody1.AppendHybridShape HybridShapePointCoord0
  wPart.InWorkObject = HybridShapePointCoord0
  wPart.Update

  Set HybridShapePointCoord1 = hypFact.AddNewPointCoord(1, 0, 0)
  HybridBody1.AppendHybridShape HybridShapePointCoord1
  wPart.InWorkObject = HybridShapePointCoord1
  wPart.Update

  Set HybridShapePointCoord2 = hypFact.AddNewPointCoord(0, 1, 0)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  Set toolCall0=absref
End Function

Function toolCall1(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2

  Set startPoint = Factory2D.CreatePoint(0, 4)
  Set endPoint = Factory2D.CreatePoint(8, 4)
  Set line = factory2d.CreateLine(0, 4, 8, 4)
  line.StartPoint = startPoint
  line.EndPoint = endPoint

  Set startPoint = Factory2D.CreatePoint(8, 4)
  Set endPoint = Factory2D.CreatePoint(8, 5.1234753829798)
  Set line = factory2d.CreateLine(8, 4, 8, 5.1234753829798)
  line.StartPoint = startPoint
  line.EndPoint = endPoint

  Set startPoint = Factory2D.CreatePoint(8, 5.1234753829798)
  Set endPoint = Factory2D.CreatePoint(6.925, 5.8046856073348)
  Set cir = Factory2D.CreateCircle(4, -4.4408920985006e-15, 6.5, 0.90792250314476, 1.1040309877476)
  cir.StartPoint = startPoint
  cir.EndPoint = endPoint

  Set startPoint = Factory2D.CreatePoint(6.925, 5.8046856073348)
  Set endPoint = Factory2D.CreatePoint(6.925, 7.8)
  Set line = factory2d.CreateLine(6.925, 5.8046856073348, 6.925, 7.8)
  line.StartPoint = startPoint
  line.EndPoint = endPoint

  Set startPoint = Factory2D.CreatePoint(6.925, 7.8)
  Set endPoint = Factory2D.CreatePoint(7.25, 7.8)
  Set line = factory2d.CreateLine(6.925, 7.8, 7.25, 7.8)
  line.StartPoint = startPoint
  line.EndPoint = endPoint

  Set startPoint = Factory2D.CreatePoint(7.25, 7.8)
  Set endPoint = Factory2D.CreatePoint(7.25, 13.617543831396)
  Set line = factory2d.CreateLine(7.25, 7.8, 7.25, 13.617543831396)
  line.StartPoint = startPoint
  line.EndPoint = endPoint

  Set startPoint = Factory2D.CreatePoint(7.25, 13.617543831396)
  Set endPoint = Factory2D.CreatePoint(0.75, 13.617543831396)
  Set cir = Factory2D.CreateCircle(4, 1.7763568394003e-14, 14, 1.3365161805512, 1.8050764730386)
  cir.StartPoint = startPoint
  cir.EndPoint = endPoint

  Set startPoint = Factory2D.CreatePoint(0.75, 13.617543831396)
  Set endPoint = Factory2D.CreatePoint(0.75, 7.8)
  Set line = factory2d.CreateLine(0.75, 13.617543831396, 0.75, 7.8)
  line.StartPoint = startPoint
  line.EndPoint = endPoint

  Set startPoint = Factory2D.CreatePoint(0.75, 7.8)
  Set endPoint = Factory2D.CreatePoint(1.075, 7.8)
  Set line = factory2d.CreateLine(0.75, 7.8, 1.075, 7.8)
  line.StartPoint = startPoint
  line.EndPoint = endPoint

  Set startPoint = Factory2D.CreatePoint(1.075, 7.8)
  Set endPoint = Factory2D.CreatePoint(1.075, 5.8046856073348)
  Set line = factory2d.CreateLine(1.075, 7.8, 1.075, 5.8046856073348)
  line.StartPoint = startPoint
  line.EndPoint = endPoint

  Set startPoint = Factory2D.CreatePoint(1.075, 5.8046856073348)
  Set endPoint = Factory2D.CreatePoint(0, 5.1234753829798)
  Set cir = Factory2D.CreateCircle(4.0000000000002, -2.5313084961454e-13, 6.5000000000003, 2.0375616658422, 2.233670150445)
  cir.StartPoint = startPoint
  cir.EndPoint = endPoint

  Set startPoint = Factory2D.CreatePoint(0, 5.1234753829798)
  Set endPoint = Factory2D.CreatePoint(0, 4)
  Set line = factory2d.CreateLine(0, 5.1234753829798, 0, 4)
  line.StartPoint = startPoint
  line.EndPoint = endPoint

  Set pk = Factory2D.CreatePoint(100, 0)
  Set pk = Factory2D.CreatePoint(-100, 0)
  Set line = Factory2d.CreateLine(100, 0, -100, 0)
  sketch.CenterLine = line

  wPart.Update

  Sketch.CloseEdition
  Set sketch3 = sketch
  wPart.Update
  Set toolCall1=sketch3
End Function

Function toolCall2(wpart,HybridBody1)
  wPart.InWorkObject = HybridBody1
  wPart.Update

  Set hypFact = wPart.HybridShapeFactory
  Set HybridShapePointCoord0 = hypFact.AddNewPointCoord(0, 0, 0)
  HybridBody1.AppendHybridShape HybridShapePointCoord0
  wPart.InWorkObject = HybridShapePointCoord0
  wPart.Update

  Set HybridShapePointCoord1 = hypFact.AddNewPointCoord(1, 0, 0)
  HybridBody1.AppendHybridShape HybridShapePointCoord1
  wPart.InWorkObject = HybridShapePointCoord1
  wPart.Update

  Set HybridShapePointCoord2 = hypFact.AddNewPointCoord(0, 0, -1)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  Set toolCall2=absref
End Function

Function toolCall3(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2

  Set startPoint = Factory2D.CreatePoint(-21, -25)
  Set endPoint = Factory2D.CreatePoint(29, -25)
  Set line = factory2d.CreateLine(-21, -25, 29, -25)
  line.StartPoint = startPoint
  line.EndPoint = endPoint

  Set startPoint = Factory2D.CreatePoint(29, -25)
  Set endPoint = Factory2D.CreatePoint(29, 25)
  Set line = factory2d.CreateLine(29, -25, 29, 25)
  line.StartPoint = startPoint
  line.EndPoint = endPoint

  Set startPoint = Factory2D.CreatePoint(29, 25)
  Set endPoint = Factory2D.CreatePoint(-21, 25)
  Set line = factory2d.CreateLine(29, 25, -21, 25)
  line.StartPoint = startPoint
  line.EndPoint = endPoint

  Set startPoint = Factory2D.CreatePoint(-21, 25)
  Set endPoint = Factory2D.CreatePoint(-21, -25)
  Set line = factory2d.CreateLine(-21, 25, -21, -25)
  line.StartPoint = startPoint
  line.EndPoint = endPoint

  Set pk = Factory2D.CreatePoint(4, 0)
  Set cir = Factory2D.CreateClosedCircle(4, 0, 12.5)

  wPart.Update

  Sketch.CloseEdition
  Set sketch5 = sketch
  wPart.Update
  Set toolCall3=sketch5
End Function

Function toolCall4(wpart,HybridBody1)
  wPart.InWorkObject = HybridBody1
  wPart.Update

  Set hypFact = wPart.HybridShapeFactory
  Set HybridShapePointCoord0 = hypFact.AddNewPointCoord(0, 0, 0)
  HybridBody1.AppendHybridShape HybridShapePointCoord0
  wPart.InWorkObject = HybridShapePointCoord0
  wPart.Update

  Set HybridShapePointCoord1 = hypFact.AddNewPointCoord(1, 0, 0)
  HybridBody1.AppendHybridShape HybridShapePointCoord1
  wPart.InWorkObject = HybridShapePointCoord1
  wPart.Update

  Set HybridShapePointCoord2 = hypFact.AddNewPointCoord(0, 1, 0)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  Set toolCall4=absref
End Function

Function toolCall5(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2

  Set startPoint = Factory2D.CreatePoint(4, -8.45)
  Set endPoint = Factory2D.CreatePoint(8, -8.45)
  Set line = factory2d.CreateLine(4, -8.45, 8, -8.45)
  line.StartPoint = startPoint
  line.EndPoint = endPoint

  Set startPoint = Factory2D.CreatePoint(8, -8.45)
  Set endPoint = Factory2D.CreatePoint(8, -21)
  Set line = factory2d.CreateLine(8, -8.45, 8, -21)
  line.StartPoint = startPoint
  line.EndPoint = endPoint

  Set startPoint = Factory2D.CreatePoint(8, -21)
  Set endPoint = Factory2D.CreatePoint(4, -21)
  Set line = factory2d.CreateLine(8, -21, 4, -21)
  line.StartPoint = startPoint
  line.EndPoint = endPoint

  Set startPoint = Factory2D.CreatePoint(4, -21)
  Set endPoint = Factory2D.CreatePoint(4, -8.45)
  Set line = factory2d.CreateLine(4, -21, 4, -8.45)
  line.StartPoint = startPoint
  line.EndPoint = endPoint

  Set pk = Factory2D.CreatePoint(4, -21)
  Set pk = Factory2D.CreatePoint(4, -8.45)
  Set line = Factory2d.CreateLine(4, -21, 4, -8.45)
  sketch.CenterLine = line

  wPart.Update

  Sketch.CloseEdition
  Set sketch7 = sketch
  wPart.Update
  Set toolCall5=sketch7
End Function

Function toolCall6(wpart,HybridBody1)
  wPart.InWorkObject = HybridBody1
  wPart.Update

  Set hypFact = wPart.HybridShapeFactory
  Set HybridShapePointCoord0 = hypFact.AddNewPointCoord(0, 0, 0)
  HybridBody1.AppendHybridShape HybridShapePointCoord0
  wPart.InWorkObject = HybridShapePointCoord0
  wPart.Update

  Set HybridShapePointCoord1 = hypFact.AddNewPointCoord(1, 0, 0)
  HybridBody1.AppendHybridShape HybridShapePointCoord1
  wPart.InWorkObject = HybridShapePointCoord1
  wPart.Update

  Set HybridShapePointCoord2 = hypFact.AddNewPointCoord(0, 1, 0)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  Set toolCall6=absref
End Function

Function toolCall7(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2

  Set startPoint = Factory2D.CreatePoint(4, -21)
  Set endPoint = Factory2D.CreatePoint(7.233, -21)
  Set line = factory2d.CreateLine(4, -21, 7.233, -21)
  line.StartPoint = startPoint
  line.EndPoint = endPoint

  Set startPoint = Factory2D.CreatePoint(7.233, -21)
  Set endPoint = Factory2D.CreatePoint(8, -21.767)
  Set line = factory2d.CreateLine(7.233, -21, 8, -21.767)
  line.StartPoint = startPoint
  line.EndPoint = endPoint

  Set startPoint = Factory2D.CreatePoint(8, -21.767)
  Set endPoint = Factory2D.CreatePoint(8, -41.233)
  Set line = factory2d.CreateLine(8, -21.767, 8, -41.233)
  line.StartPoint = startPoint
  line.EndPoint = endPoint

  Set startPoint = Factory2D.CreatePoint(8, -41.233)
  Set endPoint = Factory2D.CreatePoint(7.233, -42)
  Set line = factory2d.CreateLine(8, -41.233, 7.233, -42)
  line.StartPoint = startPoint
  line.EndPoint = endPoint

  Set startPoint = Factory2D.CreatePoint(7.233, -42)
  Set endPoint = Factory2D.CreatePoint(4, -42)
  Set line = factory2d.CreateLine(7.233, -42, 4, -42)
  line.StartPoint = startPoint
  line.EndPoint = endPoint

  Set startPoint = Factory2D.CreatePoint(4, -42)
  Set endPoint = Factory2D.CreatePoint(4, -21)
  Set line = factory2d.CreateLine(4, -42, 4, -21)
  line.StartPoint = startPoint
  line.EndPoint = endPoint

  Set pk = Factory2D.CreatePoint(4, -42)
  Set pk = Factory2D.CreatePoint(4, -21)
  Set line = Factory2d.CreateLine(4, -42, 4, -21)
  sketch.CenterLine = line

  wPart.Update

  Sketch.CloseEdition
  Set sketch9 = sketch
  wPart.Update
  Set toolCall7=sketch9
End Function

Function toolCall8(wpart,HybridBody1)
  wPart.InWorkObject = HybridBody1
  wPart.Update

  Set hypFact = wPart.HybridShapeFactory
  Set HybridShapePointCoord0 = hypFact.AddNewPointCoord(0, 0, 0)
  HybridBody1.AppendHybridShape HybridShapePointCoord0
  wPart.InWorkObject = HybridShapePointCoord0
  wPart.Update

  Set HybridShapePointCoord1 = hypFact.AddNewPointCoord(1, 0, 0)
  HybridBody1.AppendHybridShape HybridShapePointCoord1
  wPart.InWorkObject = HybridShapePointCoord1
  wPart.Update

  Set HybridShapePointCoord2 = hypFact.AddNewPointCoord(0, 1, 0)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  Set toolCall8=absref
End Function

Function toolCall9(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2

  Set startPoint = Factory2D.CreatePoint(7.25, -8.45)
  Set endPoint = Factory2D.CreatePoint(7.25, -11)
  Set line = factory2d.CreateLine(7.25, -8.45, 7.25, -11)
  line.StartPoint = startPoint
  line.EndPoint = endPoint

  Set startPoint = Factory2D.CreatePoint(7.25, -11)
  Set endPoint = Factory2D.CreatePoint(15.25, -19)
  Set line = factory2d.CreateLine(7.25, -11, 15.25, -19)
  line.StartPoint = startPoint
  line.EndPoint = endPoint

  Set startPoint = Factory2D.CreatePoint(15.25, -19)
  Set endPoint = Factory2D.CreatePoint(15.25, -8.45)
  Set line = factory2d.CreateLine(15.25, -19, 15.25, -8.45)
  line.StartPoint = startPoint
  line.EndPoint = endPoint

  Set startPoint = Factory2D.CreatePoint(15.25, -8.45)
  Set endPoint = Factory2D.CreatePoint(7.25, -8.45)
  Set line = factory2d.CreateLine(15.25, -8.45, 7.25, -8.45)
  line.StartPoint = startPoint
  line.EndPoint = endPoint

  wPart.Update

  Sketch.CloseEdition
  Set sketch11 = sketch
  wPart.Update
  Set toolCall9=sketch11
End Function

Function toolCall10(wpart,HybridBody1)
  wPart.InWorkObject = HybridBody1
  wPart.Update

  Set hypFact = wPart.HybridShapeFactory
  Set HybridShapePointCoord0 = hypFact.AddNewPointCoord(0, 0, 0)
  HybridBody1.AppendHybridShape HybridShapePointCoord0
  wPart.InWorkObject = HybridShapePointCoord0
  wPart.Update

  Set HybridShapePointCoord1 = hypFact.AddNewPointCoord(1, 0, 0)
  HybridBody1.AppendHybridShape HybridShapePointCoord1
  wPart.InWorkObject = HybridShapePointCoord1
  wPart.Update

  Set HybridShapePointCoord2 = hypFact.AddNewPointCoord(0, 1, 0)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  Set toolCall10=absref
End Function

Function toolCall11(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2

  Set startPoint = Factory2D.CreatePoint(-7.25, -19)
  Set endPoint = Factory2D.CreatePoint(0.75, -11)
  Set line = factory2d.CreateLine(-7.25, -19, 0.75, -11)
  line.StartPoint = startPoint
  line.EndPoint = endPoint

  Set startPoint = Factory2D.CreatePoint(0.75, -11)
  Set endPoint = Factory2D.CreatePoint(0.75, -8.45)
  Set line = factory2d.CreateLine(0.75, -11, 0.75, -8.45)
  line.StartPoint = startPoint
  line.EndPoint = endPoint

  Set startPoint = Factory2D.CreatePoint(0.75, -8.45)
  Set endPoint = Factory2D.CreatePoint(-7.25, -8.45)
  Set line = factory2d.CreateLine(0.75, -8.45, -7.25, -8.45)
  line.StartPoint = startPoint
  line.EndPoint = endPoint

  Set startPoint = Factory2D.CreatePoint(-7.25, -8.45)
  Set endPoint = Factory2D.CreatePoint(-7.25, -19)
  Set line = factory2d.CreateLine(-7.25, -8.45, -7.25, -19)
  line.StartPoint = startPoint
  line.EndPoint = endPoint

  wPart.Update

  Sketch.CloseEdition
  Set sketch13 = sketch
  wPart.Update
  Set toolCall11=sketch13
End Function

Sub CreatePart1
  On Error Resume Next

  Set SaveCaseDoc = CATIA.Documents.Item("SA_8_E.CATPart")

  If (Err.Number <> 0) Then
    ucaseName = GetUCaseName("SA_8_E.CATPart")
    Set SaveCaseDoc = CATIA.Documents.Item(ucaseName)
  End If

  Set PartDocument = SaveCaseDoc

  If (IsObject(PartDocument)) Then
    wPart.Activate
    Exit Sub
  End If

  Set fso = CreateObject("Scripting.FileSystemObject")

  If (fso.FileExists(storePath & "SA_8_E.CATPart")) Then
    CATIA.Documents.Open(storePath & "SA_8_E.CATPart")
    Set fso = Nothing
    Exit Sub
  ElseIf (fso.FileExists(storePath & GetUCaseName("SA_8_E.CATPart"))) Then
    CATIA.Documents.Open(storePath & GetUCaseName("SA_8_E.CATPart"))
    Set fso = Nothing
    Exit Sub
  End If

  Set fso = Nothing

  On Error Goto 0

  Set PartDocument = CATIA.Documents.Add("Part")
  Set unused1 = Partdocument.GetItem(1).UserRefProperties.CreateString("NN", "AHR_003")
  Set unused1 = Partdocument.GetItem(1).UserRefProperties.CreateString("NT", "Rod ends with a male thread")
  Set unused1 = Partdocument.GetItem(1).UserRefProperties.CreateString("NB", "SA 8 E")
  Set unused1 = Partdocument.GetItem(1).UserRefProperties.CreateString("NBSYN", "$DESIGNATION.")
  Set unused1 = Partdocument.GetItem(1).UserRefProperties.CreateString("LINA", "SA 8 E")
  Set unused1 = Partdocument.GetItem(1).UserRefProperties.CreateString("PRODUCTID", "208020002")
  Set unused1 = Partdocument.GetItem(1).UserRefProperties.CreateString("DESIGNATION", "SA 8 E")
  Set unused1 = Partdocument.GetItem(1).UserRefProperties.CreateString("DD", "8.000")
  Set unused1 = Partdocument.GetItem(1).UserRefProperties.CreateString("B", "8.000")
  Set unused1 = Partdocument.GetItem(1).UserRefProperties.CreateString("DDK", "13.000")
  Set unused1 = Partdocument.GetItem(1).UserRefProperties.CreateString("G", "M 8")
  Set unused1 = Partdocument.GetItem(1).UserRefProperties.CreateString("C1", "6.500")
  Set unused1 = Partdocument.GetItem(1).UserRefProperties.CreateString("DD2", "25.000")
  Set unused1 = Partdocument.GetItem(1).UserRefProperties.CreateString("HH", "42.000")
  Set unused1 = Partdocument.GetItem(1).UserRefProperties.CreateString("LL1", "21.000")
  Set unused1 = Partdocument.GetItem(1).UserRefProperties.CreateString("LL2", "56.000")
  Set unused1 = Partdocument.GetItem(1).UserRefProperties.CreateString("LL7", "11.000")
  Set unused1 = Partdocument.GetItem(1).UserRefProperties.CreateString("R1", "0.300")
  Set unused1 = Partdocument.GetItem(1).UserRefProperties.CreateString("AT", "15.000")
  Set unused1 = Partdocument.GetItem(1).UserRefProperties.CreateString("LOAD1", "5.500")
  Set unused1 = Partdocument.GetItem(1).UserRefProperties.CreateString("LOAD2", "12.900")
  Set unused1 = Partdocument.GetItem(1).UserRefProperties.CreateString("MASS", "0.029")
  Set unused1 = Partdocument.GetItem(1).UserRefProperties.CreateString("TYPEID", "208020")
  Set unused1 = Partdocument.GetItem(1).UserRefProperties.CreateString("TAXONOMY", "1.000")
  Set unused1 = Partdocument.GetItem(1).UserRefProperties.CreateString("BZ", "8.000")
  Set unused1 = Partdocument.GetItem(1).UserRefProperties.CreateString("GALG", "0.500")
  Set unused1 = Partdocument.GetItem(1).UserRefProperties.CreateString("TP", "1.250")
  Set unused1 = Partdocument.GetItem(1).UserRefProperties.CreateString("DESIGN", "rodend_male1")
  Set unused1 = Partdocument.GetItem(1).UserRefProperties.CreateString("MAPPING", "BAZ50,DESIGNATION|IRD01,DD|IRL01,B|IRD20,DDK|HOT01,G|HOL01A,C1|HOD01A,DD2|HOL35,HH|HOL50B,LL1|HOL40A,LL2|HOL10B,LL7|IRR20,R1|BCA10,AT|BCC02,LOAD1|HOC16,LOAD2|BAM01,MASS")
  Set unused1 = Partdocument.GetItem(1).UserRefProperties.CreateString("DESIGNLIST", "rodend_male1,rodend_male1x")
  Set unused1 = Partdocument.GetItem(1).UserRefProperties.CreateString("SORT", "DD")
  Set unused1 = Partdocument.GetItem(1).UserRefProperties.CreateString("PIM", "SA 8 E")
  Set unused1 = Partdocument.GetItem(1).UserRefProperties.CreateString("VENDOR", "SKF")
  Set unused1 = Partdocument.GetItem(1).UserRefProperties.CreateString("SUPPLIER", "SKF")
  Set unused1 = Partdocument.GetItem(1).UserRefProperties.CreateString("ARTICLENO", "SA 8 E")
  Set unused1 = Partdocument.GetItem(1).UserRefProperties.CreateString("BOMINFO", "SA 8 E")
  Set unused1 = Partdocument.GetItem(1).UserRefProperties.CreateString("CREATOR", "CADENAS GmbH")
  Partdocument.GetItem(1).PartNumber = "SA 8 E-SA 8 E"
  Partdocument.GetItem(1).Definition = "Cadenas PARTsolutions"
  Partdocument.GetItem(1).DescriptionRef = "Rod ends with a male thread"

  set wpart=partDocument.Part
  Dim skCoord(8)
  Dim Body As AnyObject
  Set Body = wPart.MainBody
  Body.Name="SA 8 E"

  Dim HybridBody1 As HybridBody
  Set HybridBody1 = wPart.HybridBodies.Add
  HybridBody1.Name="SA 8 E Geo"

  Set absref=toolCall0(wpart,HybridBody1)
  Set sketch3=toolCall1(wpart,body,absref)
  wPart.InWorkObject = Body
  wPart.Update

  Set shaft = wPart.ShapeFactory.AddNewShaft(sketch3)
  shaft.firstAngle.value = 0
  shaft.SecondAngle.value = 360
  wPart.Update

  Set absref=toolCall2(wpart,HybridBody1)
  Set sketch5=toolCall3(wpart,body,absref)
  wPart.InWorkObject = Body
  wPart.Update

  Set pocket = wPart.ShapeFactory.AddNewPocket(sketch5, 25)
  pocket.IsSymmetric = True
  wPart.Update

  Set absref=toolCall4(wpart,HybridBody1)
  Set sketch7=toolCall5(wpart,body,absref)
  wPart.InWorkObject = Body
  wPart.Update

  Set shaft = wPart.ShapeFactory.AddNewShaft(sketch7)
  shaft.firstAngle.value = 0
  shaft.SecondAngle.value = 360
  wPart.Update

  Set absref=toolCall6(wpart,HybridBody1)
  Set sketch9=toolCall7(wpart,body,absref)
  wPart.InWorkObject = Body
  wPart.Update

  Set shaft = wPart.ShapeFactory.AddNewShaft(sketch9)
  shaft.firstAngle.value = 0
  shaft.SecondAngle.value = 360
  wPart.Update

  Set absref=toolCall8(wpart,HybridBody1)
  Set sketch11=toolCall9(wpart,body,absref)
  wPart.InWorkObject = Body
  wPart.Update

  Set pocket = wPart.ShapeFactory.AddNewPocket(sketch11, 25)
  pocket.IsSymmetric = True
  wPart.Update

  Set absref=toolCall10(wpart,HybridBody1)
  Set sketch13=toolCall11(wpart,body,absref)
  wPart.InWorkObject = Body
  wPart.Update

  Set pocket = wPart.ShapeFactory.AddNewPocket(sketch13, 25)
  pocket.IsSymmetric = True
  wPart.Update

  SaveDocument PartDocument, "SA_8_E.CATPart"
End Sub

Sub CreatePsolMain
  On Error Resume Next

  Set PartDocument = CATIA.Documents.Item("SA_8_E.CATPart")

  If (IsObject(PartDocument)) Then
    wPart.Activate
    Exit Sub
  End If

  If (IsEmpty(readSPath)) Then
    Exit Sub
  End If

  Set fso = CreateObject("Scripting.FileSystemObject")

  If (fso.FileExists(storePath & "SA_8_E.CATPart")) Then
    CATIA.Documents.Open(storePath & "SA_8_E.CATPart")
    Set fso = Nothing
    Exit Sub
  End If

  Set fso = Nothing

  On Error Goto 0

  CreatePart1


End Sub

CreatePsolMain
