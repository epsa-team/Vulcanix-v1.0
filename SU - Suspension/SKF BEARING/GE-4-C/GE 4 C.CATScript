Dim storePath as String

' Sub to read the Store Path
Function ReadSPath()
  os = UCase(Left(CATIA.SystemConfiguration.OperatingSystem, 3))
  sep = "/"
  If (os = "WIN") Or (os = "INT") Then
    sep = "\"
  End If

  If (Len(storePath) = 0) Then
    ret = InputBox("Enter Path for CATPart or CATProduct (e.g. c:" + sep + "catfiles" + sep + ")", "Save as")
    storePath = ret
  End If

  Set fso = CreateObject("Scripting.FileSystemObject")

  If (Len(storePath) = 0) Or (fso.FolderExists(storePath) = False) Then
    Set fso = Nothing
    ReadSPath = Empty
    Exit Function
  End If

  If (Mid(storePath, Len(storePath), 1) <> sep) Then
    storePath = storePath + sep
  End If

  ReadSPath = storePath
  Set fso = Nothing
End Function

' Sub to store a document'
Sub SaveDocument(document, name)
  document.SaveAs storePath & name
End Sub

' Sub to retrieve a name in capital letters'
Function GetUCaseName(name)
  ucaseName = Left(name, InStrRev(name, ".") - 1)
  extension = Right(name, Len(name) - InStr(name, ".") + 1)
  GetUCaseName = UCase(ucaseName) + extension
End Function

Function toolCall0(wpart,HybridBody1)
  wPart.InWorkObject = HybridBody1
  wPart.Update

  Set hypFact = wPart.HybridShapeFactory
  Set HybridShapePointCoord0 = hypFact.AddNewPointCoord(0, 0, 0)
  HybridBody1.AppendHybridShape HybridShapePointCoord0
  wPart.InWorkObject = HybridShapePointCoord0
  wPart.Update

  Set HybridShapePointCoord1 = hypFact.AddNewPointCoord(1, 0, 0)
  HybridBody1.AppendHybridShape HybridShapePointCoord1
  wPart.InWorkObject = HybridShapePointCoord1
  wPart.Update

  Set HybridShapePointCoord2 = hypFact.AddNewPointCoord(0, 1, 0)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  Set toolCall0=absref
End Function

Function toolCall1(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2

  Set startPoint = Factory2D.CreatePoint(0, 2.3)
  Set endPoint = Factory2D.CreatePoint(0.3, 2)
  Set cir = Factory2D.CreateCircle(0.3, 2.3, 0.3, 3.1415926535898, 4.7123889803847)
  cir.StartPoint = startPoint
  cir.EndPoint = endPoint

  Set startPoint = Factory2D.CreatePoint(0.3, 2)
  Set endPoint = Factory2D.CreatePoint(4.7, 2)
  Set line = factory2d.CreateLine(0.3, 2, 4.7, 2)
  line.StartPoint = startPoint
  line.EndPoint = endPoint

  Set startPoint = Factory2D.CreatePoint(4.7, 2)
  Set endPoint = Factory2D.CreatePoint(5, 2.3)
  Set cir = Factory2D.CreateCircle(4.7, 2.3, 0.3, 4.7123889803847, 0)
  cir.StartPoint = startPoint
  cir.EndPoint = endPoint

  Set startPoint = Factory2D.CreatePoint(5, 2.3)
  Set endPoint = Factory2D.CreatePoint(5, 3.1224989991992)
  Set line = factory2d.CreateLine(5, 2.3, 5, 3.1224989991992)
  line.StartPoint = startPoint
  line.EndPoint = endPoint

  Set startPoint = Factory2D.CreatePoint(5, 3.1224989991992)
  Set endPoint = Factory2D.CreatePoint(0, 3.1224989991992)
  Set cir = Factory2D.CreateCircle(2.5, 0, 4, 0.89566479385787, 2.2459278597319)
  cir.StartPoint = startPoint
  cir.EndPoint = endPoint

  Set startPoint = Factory2D.CreatePoint(0, 3.1224989991992)
  Set endPoint = Factory2D.CreatePoint(0, 2.3)
  Set line = factory2d.CreateLine(0, 3.1224989991992, 0, 2.3)
  line.StartPoint = startPoint
  line.EndPoint = endPoint

  Set pk = Factory2D.CreatePoint(1.25, 0)
  Set pk = Factory2D.CreatePoint(-1.25, 0)
  Set line = Factory2d.CreateLine(1.25, 0, -1.25, 0)
  sketch.CenterLine = line

  wPart.Update

  Sketch.CloseEdition
  Set sketch3 = sketch
  wPart.Update
  Set toolCall1=sketch3
End Function

Function toolCall2(wpart,HybridBody1)
  wPart.InWorkObject = HybridBody1
  wPart.Update

  Set hypFact = wPart.HybridShapeFactory
  Set HybridShapePointCoord0 = hypFact.AddNewPointCoord(0, 0, 0)
  HybridBody1.AppendHybridShape HybridShapePointCoord0
  wPart.InWorkObject = HybridShapePointCoord0
  wPart.Update

  Set HybridShapePointCoord1 = hypFact.AddNewPointCoord(1, 0, 0)
  HybridBody1.AppendHybridShape HybridShapePointCoord1
  wPart.InWorkObject = HybridShapePointCoord1
  wPart.Update

  Set HybridShapePointCoord2 = hypFact.AddNewPointCoord(0, 1, 0)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  Set toolCall2=absref
End Function

Function toolCall3(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2

  Set startPoint = Factory2D.CreatePoint(4, 3.7080992435478)
  Set endPoint = Factory2D.CreatePoint(1, 3.7080992435478)
  Set cir = Factory2D.CreateCircle(2.5, 8.8817841970013e-16, 4, 1.1863995522993, 1.9551931012905)
  cir.StartPoint = startPoint
  cir.EndPoint = endPoint

  Set startPoint = Factory2D.CreatePoint(4, 3.7080992435478)
  Set endPoint = Factory2D.CreatePoint(4, 5.7)
  Set line = factory2d.CreateLine(4, 3.7080992435478, 4, 5.7)
  line.StartPoint = startPoint
  line.EndPoint = endPoint

  Set startPoint = Factory2D.CreatePoint(4, 5.7)
  Set endPoint = Factory2D.CreatePoint(3.7, 6)
  Set cir = Factory2D.CreateCircle(3.7, 5.7, 0.3, 0, 1.5707963267949)
  cir.StartPoint = startPoint
  cir.EndPoint = endPoint

  Set startPoint = Factory2D.CreatePoint(3.7, 6)
  Set endPoint = Factory2D.CreatePoint(1.3, 6)
  Set line = factory2d.CreateLine(3.7, 6, 1.3, 6)
  line.StartPoint = startPoint
  line.EndPoint = endPoint

  Set startPoint = Factory2D.CreatePoint(1.3, 6)
  Set endPoint = Factory2D.CreatePoint(1, 5.7)
  Set cir = Factory2D.CreateCircle(1.3, 5.7, 0.3, 1.5707963267949, 3.1415926386886)
  cir.StartPoint = startPoint
  cir.EndPoint = endPoint

  Set startPoint = Factory2D.CreatePoint(1, 5.7)
  Set endPoint = Factory2D.CreatePoint(1, 3.7080992435478)
  Set line = factory2d.CreateLine(1, 5.7, 1, 3.7080992435478)
  line.StartPoint = startPoint
  line.EndPoint = endPoint

  Set pk = Factory2D.CreatePoint(4, 0)
  Set pk = Factory2D.CreatePoint(1, 0)
  Set line = Factory2d.CreateLine(4, 0, 1, 0)
  sketch.CenterLine = line

  wPart.Update

  Sketch.CloseEdition
  Set sketch3 = sketch
  wPart.Update
  Set toolCall3=sketch3
End Function

Sub CreatePart1
  On Error Resume Next

  Set SaveCaseDoc = CATIA.Documents.Item("GE_4_Cblr_001_101_spb_ge1.CATPart")

  If (Err.Number <> 0) Then
    ucaseName = GetUCaseName("GE_4_Cblr_001_101_spb_ge1.CATPart")
    Set SaveCaseDoc = CATIA.Documents.Item(ucaseName)
  End If

  Set PartDocument = SaveCaseDoc

  If (IsObject(PartDocument)) Then
    wPart.Activate
    Exit Sub
  End If

  Set fso = CreateObject("Scripting.FileSystemObject")

  If (fso.FileExists(storePath & "GE_4_Cblr_001_101_spb_ge1.CATPart")) Then
    CATIA.Documents.Open(storePath & "GE_4_Cblr_001_101_spb_ge1.CATPart")
    Set fso = Nothing
    Exit Sub
  ElseIf (fso.FileExists(storePath & GetUCaseName("GE_4_Cblr_001_101_spb_ge1.CATPart"))) Then
    CATIA.Documents.Open(storePath & GetUCaseName("GE_4_Cblr_001_101_spb_ge1.CATPart"))
    Set fso = Nothing
    Exit Sub
  End If

  Set fso = Nothing

  On Error Goto 0

  Set PartDocument = CATIA.Documents.Add("Part")
  Set unused1 = Partdocument.GetItem(1).UserRefProperties.CreateString("NN", "BLR_001_101blr_001_101_spb_ge1")
  Set unused1 = Partdocument.GetItem(1).UserRefProperties.CreateString("NT", "Radial spherical plain bearings")
  Set unused1 = Partdocument.GetItem(1).UserRefProperties.CreateString("NB", "GE 4 Cblr_001_101_spb_ge1")
  Set unused1 = Partdocument.GetItem(1).UserRefProperties.CreateString("NBSYN", "$DESIGNATION.blr_001_101_spb_ge1")
  Set unused1 = Partdocument.GetItem(1).UserRefProperties.CreateString("LINA", "GE 4 Cblr_001_101_spb_ge1")
  Set unused1 = Partdocument.GetItem(1).UserRefProperties.CreateString("PRODUCTID", "183200004")
  Set unused1 = Partdocument.GetItem(1).UserRefProperties.CreateString("DESIGNATION", "GE 4 C")
  Set unused1 = Partdocument.GetItem(1).UserRefProperties.CreateString("DD", "4.000")
  Set unused1 = Partdocument.GetItem(1).UserRefProperties.CreateString("D", "12.000")
  Set unused1 = Partdocument.GetItem(1).UserRefProperties.CreateString("B", "5.000")
  Set unused1 = Partdocument.GetItem(1).UserRefProperties.CreateString("C", "3.000")
  Set unused1 = Partdocument.GetItem(1).UserRefProperties.CreateString("I", "16.000")
  Set unused1 = Partdocument.GetItem(1).UserRefProperties.CreateString("DK", "8.000")
  Set unused1 = Partdocument.GetItem(1).UserRefProperties.CreateString("R1", "0.300")
  Set unused1 = Partdocument.GetItem(1).UserRefProperties.CreateString("R2", "0.300")
  Set unused1 = Partdocument.GetItem(1).UserRefProperties.CreateString("LOAD1", "2.160")
  Set unused1 = Partdocument.GetItem(1).UserRefProperties.CreateString("LOAD2", "5.400")
  Set unused1 = Partdocument.GetItem(1).UserRefProperties.CreateString("MASS", "0.003")
  Set unused1 = Partdocument.GetItem(1).UserRefProperties.CreateString("TYPEID", "183200")
  Set unused1 = Partdocument.GetItem(1).UserRefProperties.CreateString("TAXONOMY", "1")
  Set unused1 = Partdocument.GetItem(1).UserRefProperties.CreateString("DESIGN", "spb_ge")
  Set unused1 = Partdocument.GetItem(1).UserRefProperties.CreateString("PPATH", "blr_001_101_asmtpl.prj")
  Set unused1 = Partdocument.GetItem(1).UserRefProperties.CreateString("MAPPING", "BCZ50,DESIGNATION|IRD01,DD|ORD10,D|BCW30,B|ORL01,C|BCA10,I|IRD20,DK|IRD30,DD1|IRR20,R1|ORR20,R2|ORL52,BB|IRL52,BB1|ORD55,M|BCC02,LOAD1|BCC16,LOAD2|BCM01,MASS")
  Set unused1 = Partdocument.GetItem(1).UserRefProperties.CreateString("DESIGNLIST", "spb_ge,spb_geg")
  Set unused1 = Partdocument.GetItem(1).UserRefProperties.CreateString("SORT", "DD")
  Set unused1 = Partdocument.GetItem(1).UserRefProperties.CreateString("PIM", "GE 4 C")
  Set unused1 = Partdocument.GetItem(1).UserRefProperties.CreateString("COPYTABLE", "blr_001_101_dummy,blr_001_101_spb_ge1,blr_001_101_spb_ge2,blr_001_101_spb_geg1,blr_001_101_spb_geg2")
  Set unused1 = Partdocument.GetItem(1).UserRefProperties.CreateString("VENDOR", "SKF")
  Set unused1 = Partdocument.GetItem(1).UserRefProperties.CreateString("SUPPLIER", "SKF")
  Set unused1 = Partdocument.GetItem(1).UserRefProperties.CreateString("ARTICLENO", "GE 4 Cblr_001_101_spb_ge1")
  Set unused1 = Partdocument.GetItem(1).UserRefProperties.CreateString("BOMINFO", "GE 4 Cblr_001_101_spb_ge1")
  Set unused1 = Partdocument.GetItem(1).UserRefProperties.CreateString("CREATOR", "CADENAS GmbH")
  Partdocument.GetItem(1).PartNumber = "GE 4 Cblr_001_101_spb_ge1-GE 4 Cblr_001_101_spb_ge1"
  Partdocument.GetItem(1).Definition = "Cadenas PARTsolutions"
  Partdocument.GetItem(1).DescriptionRef = "Radial spherical plain bearings"

  set wpart=partDocument.Part
  Dim skCoord(8)
  Dim Body As AnyObject
  Set Body = wPart.MainBody
  Body.Name="GE 4 Cblr_001_101_spb_ge1"

  Dim HybridBody1 As HybridBody
  Set HybridBody1 = wPart.HybridBodies.Add
  HybridBody1.Name="GE 4 Cblr_001_101_spb_ge1 Geo"

  Set absref=toolCall0(wpart,HybridBody1)
  Set sketch3=toolCall1(wpart,body,absref)
  wPart.InWorkObject = Body
  wPart.Update

  Set shaft = wPart.ShapeFactory.AddNewShaft(sketch3)
  shaft.firstAngle.value = 0
  shaft.SecondAngle.value = 360
  wPart.Update

  SaveDocument PartDocument, "GE_4_Cblr_001_101_spb_ge1.CATPart"
End Sub


Sub CreatePart2
  On Error Resume Next

  Set SaveCaseDoc = CATIA.Documents.Item("GE_4_Cblr_001_101_spb_ge2.CATPart")

  If (Err.Number <> 0) Then
    ucaseName = GetUCaseName("GE_4_Cblr_001_101_spb_ge2.CATPart")
    Set SaveCaseDoc = CATIA.Documents.Item(ucaseName)
  End If

  Set PartDocument = SaveCaseDoc

  If (IsObject(PartDocument)) Then
    wPart.Activate
    Exit Sub
  End If

  Set fso = CreateObject("Scripting.FileSystemObject")

  If (fso.FileExists(storePath & "GE_4_Cblr_001_101_spb_ge2.CATPart")) Then
    CATIA.Documents.Open(storePath & "GE_4_Cblr_001_101_spb_ge2.CATPart")
    Set fso = Nothing
    Exit Sub
  ElseIf (fso.FileExists(storePath & GetUCaseName("GE_4_Cblr_001_101_spb_ge2.CATPart"))) Then
    CATIA.Documents.Open(storePath & GetUCaseName("GE_4_Cblr_001_101_spb_ge2.CATPart"))
    Set fso = Nothing
    Exit Sub
  End If

  Set fso = Nothing

  On Error Goto 0

  Set PartDocument = CATIA.Documents.Add("Part")
  Set unused1 = Partdocument.GetItem(1).UserRefProperties.CreateString("NN", "BLR_001_101blr_001_101_spb_ge2")
  Set unused1 = Partdocument.GetItem(1).UserRefProperties.CreateString("NT", "Radial spherical plain bearings")
  Set unused1 = Partdocument.GetItem(1).UserRefProperties.CreateString("NB", "GE 4 Cblr_001_101_spb_ge2")
  Set unused1 = Partdocument.GetItem(1).UserRefProperties.CreateString("NBSYN", "$DESIGNATION.blr_001_101_spb_ge2")
  Set unused1 = Partdocument.GetItem(1).UserRefProperties.CreateString("LINA", "GE 4 Cblr_001_101_spb_ge2")
  Set unused1 = Partdocument.GetItem(1).UserRefProperties.CreateString("PRODUCTID", "183200004")
  Set unused1 = Partdocument.GetItem(1).UserRefProperties.CreateString("DESIGNATION", "GE 4 C")
  Set unused1 = Partdocument.GetItem(1).UserRefProperties.CreateString("DD", "4.000")
  Set unused1 = Partdocument.GetItem(1).UserRefProperties.CreateString("D", "12.000")
  Set unused1 = Partdocument.GetItem(1).UserRefProperties.CreateString("B", "5.000")
  Set unused1 = Partdocument.GetItem(1).UserRefProperties.CreateString("C", "3.000")
  Set unused1 = Partdocument.GetItem(1).UserRefProperties.CreateString("I", "16.000")
  Set unused1 = Partdocument.GetItem(1).UserRefProperties.CreateString("DK", "8.000")
  Set unused1 = Partdocument.GetItem(1).UserRefProperties.CreateString("R1", "0.300")
  Set unused1 = Partdocument.GetItem(1).UserRefProperties.CreateString("R2", "0.300")
  Set unused1 = Partdocument.GetItem(1).UserRefProperties.CreateString("LOAD1", "2.160")
  Set unused1 = Partdocument.GetItem(1).UserRefProperties.CreateString("LOAD2", "5.400")
  Set unused1 = Partdocument.GetItem(1).UserRefProperties.CreateString("MASS", "0.003")
  Set unused1 = Partdocument.GetItem(1).UserRefProperties.CreateString("TYPEID", "183200")
  Set unused1 = Partdocument.GetItem(1).UserRefProperties.CreateString("TAXONOMY", "1")
  Set unused1 = Partdocument.GetItem(1).UserRefProperties.CreateString("DESIGN", "spb_ge")
  Set unused1 = Partdocument.GetItem(1).UserRefProperties.CreateString("PPATH", "blr_001_101_asmtpl.prj")
  Set unused1 = Partdocument.GetItem(1).UserRefProperties.CreateString("MAPPING", "BCZ50,DESIGNATION|IRD01,DD|ORD10,D|BCW30,B|ORL01,C|BCA10,I|IRD20,DK|IRD30,DD1|IRR20,R1|ORR20,R2|ORL52,BB|IRL52,BB1|ORD55,M|BCC02,LOAD1|BCC16,LOAD2|BCM01,MASS")
  Set unused1 = Partdocument.GetItem(1).UserRefProperties.CreateString("DESIGNLIST", "spb_ge,spb_geg")
  Set unused1 = Partdocument.GetItem(1).UserRefProperties.CreateString("SORT", "DD")
  Set unused1 = Partdocument.GetItem(1).UserRefProperties.CreateString("PIM", "GE 4 C")
  Set unused1 = Partdocument.GetItem(1).UserRefProperties.CreateString("COPYTABLE", "blr_001_101_dummy,blr_001_101_spb_ge1,blr_001_101_spb_ge2,blr_001_101_spb_geg1,blr_001_101_spb_geg2")
  Set unused1 = Partdocument.GetItem(1).UserRefProperties.CreateString("VENDOR", "SKF")
  Set unused1 = Partdocument.GetItem(1).UserRefProperties.CreateString("SUPPLIER", "SKF")
  Set unused1 = Partdocument.GetItem(1).UserRefProperties.CreateString("ARTICLENO", "GE 4 Cblr_001_101_spb_ge2")
  Set unused1 = Partdocument.GetItem(1).UserRefProperties.CreateString("BOMINFO", "GE 4 Cblr_001_101_spb_ge2")
  Set unused1 = Partdocument.GetItem(1).UserRefProperties.CreateString("CREATOR", "CADENAS GmbH")
  Partdocument.GetItem(1).PartNumber = "GE 4 Cblr_001_101_spb_ge2-GE 4 Cblr_001_101_spb_ge2"
  Partdocument.GetItem(1).Definition = "Cadenas PARTsolutions"
  Partdocument.GetItem(1).DescriptionRef = "Radial spherical plain bearings"

  set wpart=partDocument.Part
  Dim skCoord(8)
  Dim Body As AnyObject
  Set Body = wPart.MainBody
  Body.Name="GE 4 Cblr_001_101_spb_ge2"

  Dim HybridBody1 As HybridBody
  Set HybridBody1 = wPart.HybridBodies.Add
  HybridBody1.Name="GE 4 Cblr_001_101_spb_ge2 Geo"

  Set absref=toolCall2(wpart,HybridBody1)
  Set sketch3=toolCall3(wpart,body,absref)
  wPart.InWorkObject = Body
  wPart.Update

  Set shaft = wPart.ShapeFactory.AddNewShaft(sketch3)
  shaft.firstAngle.value = 0
  shaft.SecondAngle.value = 360
  wPart.Update

  SaveDocument PartDocument, "GE_4_Cblr_001_101_spb_ge2.CATPart"
End Sub


' Create Assembly
Sub CreateAsm2
  On Error Resume Next

  Set SaveCaseDoc = CATIA.Documents.Item("GE_4_C.CATProduct")

  If (Err.Number <> 0) Then
    ucaseName = GetUCaseName("GE_4_C.CATProduct")
    Set SaveCaseDoc = CATIA.Documents.Item(ucaseName)
  End If

  Set PartDocument = SaveCaseDoc

  If (IsObject(PartDocument)) Then
    wPart.Activate
    Exit Sub
  End If

  Set fso = CreateObject("Scripting.FileSystemObject")

  If (fso.FileExists(storePath & "GE_4_C.CATProduct")) Then
    CATIA.Documents.Open(storePath & "GE_4_C.CATProduct")
    Set fso = Nothing
    Exit Sub
  ElseIf (fso.FileExists(storePath & GetUCaseName("GE_4_C.CATProduct"))) Then
    CATIA.Documents.Open(storePath & GetUCaseName("GE_4_C.CATProduct"))
    Set fso = Nothing
    Exit Sub
  End If

  Set fso = Nothing

  On Error Goto 0

  Dim mat(11)
  Dim pin(0)
  Dim docName As String
  Set ProductDocument = CATIA.Documents.Add("Product")
  Dim Product As AnyObject
  Set Product = ProductDocument.Product

  Set unused1 = Product.UserRefProperties.CreateString("NN", "BLR_001_101")
  Set unused1 = Product.UserRefProperties.CreateString("NT", "Radial spherical plain bearings")
  Set unused1 = Product.UserRefProperties.CreateString("NB", "GE 4 C")
  Set unused1 = Product.UserRefProperties.CreateString("NBSYN", "$DESIGNATION.")
  Set unused1 = Product.UserRefProperties.CreateString("LINA", "GE 4 C")
  Set unused1 = Product.UserRefProperties.CreateString("PRODUCTID", "183200004")
  Set unused1 = Product.UserRefProperties.CreateString("DESIGNATION", "GE 4 C")
  Set unused1 = Product.UserRefProperties.CreateString("DD", "4.000")
  Set unused1 = Product.UserRefProperties.CreateString("D", "12.000")
  Set unused1 = Product.UserRefProperties.CreateString("B", "5.000")
  Set unused1 = Product.UserRefProperties.CreateString("C", "3.000")
  Set unused1 = Product.UserRefProperties.CreateString("I", "16.000")
  Set unused1 = Product.UserRefProperties.CreateString("DK", "8.000")
  Set unused1 = Product.UserRefProperties.CreateString("R1", "0.300")
  Set unused1 = Product.UserRefProperties.CreateString("R2", "0.300")
  Set unused1 = Product.UserRefProperties.CreateString("LOAD1", "2.160")
  Set unused1 = Product.UserRefProperties.CreateString("LOAD2", "5.400")
  Set unused1 = Product.UserRefProperties.CreateString("MASS", "0.003")
  Set unused1 = Product.UserRefProperties.CreateString("TYPEID", "183200")
  Set unused1 = Product.UserRefProperties.CreateString("TAXONOMY", "1")
  Set unused1 = Product.UserRefProperties.CreateString("DESIGN", "spb_ge")
  Set unused1 = Product.UserRefProperties.CreateString("PPATH", "blr_001_101_asmtpl.prj")
  Set unused1 = Product.UserRefProperties.CreateString("MAPPING", "BCZ50,DESIGNATION|IRD01,DD|ORD10,D|BCW30,B|ORL01,C|BCA10,I|IRD20,DK|IRD30,DD1|IRR20,R1|ORR20,R2|ORL52,BB|IRL52,BB1|ORD55,M|BCC02,LOAD1|BCC16,LOAD2|BCM01,MASS")
  Set unused1 = Product.UserRefProperties.CreateString("DESIGNLIST", "spb_ge,spb_geg")
  Set unused1 = Product.UserRefProperties.CreateString("SORT", "DD")
  Set unused1 = Product.UserRefProperties.CreateString("PIM", "GE 4 C")
  Set unused1 = Product.UserRefProperties.CreateString("COPYTABLE", "blr_001_101_dummy,blr_001_101_spb_ge1,blr_001_101_spb_ge2,blr_001_101_spb_geg1,blr_001_101_spb_geg2")
  Set unused1 = Product.UserRefProperties.CreateString("HIDE", "0")
  Set unused1 = Product.UserRefProperties.CreateString("VENDOR", "SKF")
  Set unused1 = Product.UserRefProperties.CreateString("SUPPLIER", "SKF")
  Set unused1 = Product.UserRefProperties.CreateString("ARTICLENO", "GE 4 C")
  Set unused1 = Product.UserRefProperties.CreateString("BOMINFO", "GE 4 C")
  Set unused1 = Product.UserRefProperties.CreateString("CREATOR", "CADENAS GmbH")
  Product.PartNumber = "GE 4 C-GE 4 C"
  Product.Definition = "Cadenas PARTsolutions"
  Product.DescriptionRef = "Radial spherical plain bearings"

  mat( 0) = 1.000000
  mat( 1) = 0.000000
  mat( 2) = 0.000000
  mat( 3) = 0.000000
  mat( 4) = 1.000000
  mat( 5) = 0.000000
  mat( 6) = 0.000000
  mat( 7) = 0.000000
  mat( 8) = 1.000000
  mat( 9) = 0.000000
  mat(10) = 0.000000
  mat(11) = 0.000000
  On Error Resume Next

  Set SaveCaseDoc = CATIA.Documents.Item("GE_4_Cblr_001_101_spb_ge1.CATPart")

  If (Err.Number <> 0) Then
    ucaseName = GetUCaseName("GE_4_Cblr_001_101_spb_ge1.CATPart")
    Set SaveCaseDoc = CATIA.Documents.Item(ucaseName)
  End If

  Set newProd = Product.Products.AddComponent(SaveCaseDoc.GetItem(1))
  NewProd.Move.Apply mat

  mat( 0) = 1.000000
  mat( 1) = 0.000000
  mat( 2) = 0.000000
  mat( 3) = 0.000000
  mat( 4) = 1.000000
  mat( 5) = 0.000000
  mat( 6) = 0.000000
  mat( 7) = 0.000000
  mat( 8) = 1.000000
  mat( 9) = 0.000000
  mat(10) = 0.000000
  mat(11) = 0.000000
  On Error Resume Next

  Set SaveCaseDoc = CATIA.Documents.Item("GE_4_Cblr_001_101_spb_ge2.CATPart")

  If (Err.Number <> 0) Then
    ucaseName = GetUCaseName("GE_4_Cblr_001_101_spb_ge2.CATPart")
    Set SaveCaseDoc = CATIA.Documents.Item(ucaseName)
  End If

  Set newProd = Product.Products.AddComponent(SaveCaseDoc.GetItem(1))
  NewProd.Move.Apply mat


  On Error Resume Next

  Set SaveCaseDoc = CATIA.Documents.Item("GE_4_Cblr_001_101_spb_ge1.CATPart")

  If (Err.Number <> 0) Then
    ucaseName = GetUCaseName("GE_4_Cblr_001_101_spb_ge1.CATPart")
    Set SaveCaseDoc = CATIA.Documents.Item(ucaseName)
  End If

  SaveCaseDoc.Close

  On Error Resume Next

  Set SaveCaseDoc = CATIA.Documents.Item("GE_4_Cblr_001_101_spb_ge2.CATPart")

  If (Err.Number <> 0) Then
    ucaseName = GetUCaseName("GE_4_Cblr_001_101_spb_ge2.CATPart")
    Set SaveCaseDoc = CATIA.Documents.Item(ucaseName)
  End If

  SaveCaseDoc.Close
  SaveDocument ProductDocument, "GE_4_C.CATProduct"
End Sub

Sub CreatePsolMain
  On Error Resume Next

  Set PartDocument = CATIA.Documents.Item("GE_4_C.CATProduct")

  If (IsObject(PartDocument)) Then
    wPart.Activate
    Exit Sub
  End If

  If (IsEmpty(readSPath)) Then
    Exit Sub
  End If

  Set fso = CreateObject("Scripting.FileSystemObject")

  If (fso.FileExists(storePath & "GE_4_C.CATProduct")) Then
    CATIA.Documents.Open(storePath & "GE_4_C.CATProduct")
    Set fso = Nothing
    Exit Sub
  End If

  Set fso = Nothing

  On Error Goto 0

  CreatePart1
  CreatePart2
  CreateAsm2


End Sub

CreatePsolMain
