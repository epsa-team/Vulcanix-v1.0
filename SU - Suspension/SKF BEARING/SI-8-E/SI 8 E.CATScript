Dim storePath as String

' Sub to read the Store Path
Function ReadSPath()
  os = UCase(Left(CATIA.SystemConfiguration.OperatingSystem, 3))
  sep = "/"
  If (os = "WIN") Or (os = "INT") Then
    sep = "\"
  End If

  If (Len(storePath) = 0) Then
    ret = InputBox("Enter Path for CATPart or CATProduct (e.g. c:" + sep + "catfiles" + sep + ")", "Save as")
    storePath = ret
  End If

  Set fso = CreateObject("Scripting.FileSystemObject")

  If (Len(storePath) = 0) Or (fso.FolderExists(storePath) = False) Then
    Set fso = Nothing
    ReadSPath = Empty
    Exit Function
  End If

  If (Mid(storePath, Len(storePath), 1) <> sep) Then
    storePath = storePath + sep
  End If

  ReadSPath = storePath
  Set fso = Nothing
End Function

' Sub to store a document'
Sub SaveDocument(document, name)
  document.SaveAs storePath & name
End Sub

' Sub to retrieve a name in capital letters'
Function GetUCaseName(name)
  ucaseName = Left(name, InStrRev(name, ".") - 1)
  extension = Right(name, Len(name) - InStr(name, ".") + 1)
  GetUCaseName = UCase(ucaseName) + extension
End Function

Function toolCall0(wpart,HybridBody1)
  wPart.InWorkObject = HybridBody1
  wPart.Update

  Set hypFact = wPart.HybridShapeFactory
  Set HybridShapePointCoord0 = hypFact.AddNewPointCoord(0, 0, 0)
  HybridBody1.AppendHybridShape HybridShapePointCoord0
  wPart.InWorkObject = HybridShapePointCoord0
  wPart.Update

  Set HybridShapePointCoord1 = hypFact.AddNewPointCoord(1, 0, 0)
  HybridBody1.AppendHybridShape HybridShapePointCoord1
  wPart.InWorkObject = HybridShapePointCoord1
  wPart.Update

  Set HybridShapePointCoord2 = hypFact.AddNewPointCoord(0, 1, 0)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  Set toolCall0=absref
End Function

Function toolCall1(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2

  Set startPoint = Factory2D.CreatePoint(0, 4.3)
  Set endPoint = Factory2D.CreatePoint(0.3, 4)
  Set cir = Factory2D.CreateCircle(0.3, 4.3, 0.3, 3.1415926535898, 4.7123889803847)
  cir.StartPoint = startPoint
  cir.EndPoint = endPoint

  Set startPoint = Factory2D.CreatePoint(0.3, 4)
  Set endPoint = Factory2D.CreatePoint(7.7, 4)
  Set line = factory2d.CreateLine(0.3, 4, 7.7, 4)
  line.StartPoint = startPoint
  line.EndPoint = endPoint

  Set startPoint = Factory2D.CreatePoint(7.7, 4)
  Set endPoint = Factory2D.CreatePoint(8, 4.3)
  Set cir = Factory2D.CreateCircle(7.7, 4.3, 0.3, 4.7123889803847, 1.4901161193848e-08)
  cir.StartPoint = startPoint
  cir.EndPoint = endPoint

  Set startPoint = Factory2D.CreatePoint(8, 4.3)
  Set endPoint = Factory2D.CreatePoint(8, 5.1234753829798)
  Set line = factory2d.CreateLine(8, 4.3, 8, 5.1234753829798)
  line.StartPoint = startPoint
  line.EndPoint = endPoint

  Set startPoint = Factory2D.CreatePoint(8, 5.1234753829798)
  Set endPoint = Factory2D.CreatePoint(7.0875, 5.7199076697094)
  Set cir = Factory2D.CreateCircle(3.9999999999998, -3.0286884111774e-13, 6.5000000000004, 0.90792250314476, 1.075832295078)
  cir.StartPoint = startPoint
  cir.EndPoint = endPoint

  Set startPoint = Factory2D.CreatePoint(7.0875, 5.7199076697094)
  Set endPoint = Factory2D.CreatePoint(7.0875, 7.5)
  Set line = factory2d.CreateLine(7.0875, 5.7199076697094, 7.0875, 7.5)
  line.StartPoint = startPoint
  line.EndPoint = endPoint

  Set startPoint = Factory2D.CreatePoint(7.0875, 7.5)
  Set endPoint = Factory2D.CreatePoint(6.7875, 7.8)
  Set cir = Factory2D.CreateCircle(6.7875, 7.5, 0.3, 0, 1.5707963267949)
  cir.StartPoint = startPoint
  cir.EndPoint = endPoint

  Set startPoint = Factory2D.CreatePoint(6.7875, 7.8)
  Set endPoint = Factory2D.CreatePoint(1.2125, 7.8)
  Set line = factory2d.CreateLine(6.7875, 7.8, 1.2125, 7.8)
  line.StartPoint = startPoint
  line.EndPoint = endPoint

  Set startPoint = Factory2D.CreatePoint(1.2125, 7.8)
  Set endPoint = Factory2D.CreatePoint(0.9125, 7.5)
  Set cir = Factory2D.CreateCircle(1.2125, 7.5, 0.3, 1.5707963267949, 3.1415926535898)
  cir.StartPoint = startPoint
  cir.EndPoint = endPoint

  Set startPoint = Factory2D.CreatePoint(0.9125, 7.5)
  Set endPoint = Factory2D.CreatePoint(0.9125, 5.7199076697094)
  Set line = factory2d.CreateLine(0.9125, 7.5, 0.9125, 5.7199076697094)
  line.StartPoint = startPoint
  line.EndPoint = endPoint

  Set startPoint = Factory2D.CreatePoint(0.9125, 5.7199076697094)
  Set endPoint = Factory2D.CreatePoint(0, 5.1234753829798)
  Set cir = Factory2D.CreateCircle(4, 6.6613381477509e-14, 6.4999999999999, 2.0657603585118, 2.233670150445)
  cir.StartPoint = startPoint
  cir.EndPoint = endPoint

  Set startPoint = Factory2D.CreatePoint(0, 5.1234753829798)
  Set endPoint = Factory2D.CreatePoint(0, 4.3)
  Set line = factory2d.CreateLine(0, 5.1234753829798, 0, 4.3)
  line.StartPoint = startPoint
  line.EndPoint = endPoint

  Set pk = Factory2D.CreatePoint(50, 0)
  Set pk = Factory2D.CreatePoint(-50, 0)
  Set line = Factory2d.CreateLine(50, 0, -50, 0)
  sketch.CenterLine = line

  wPart.Update

  Sketch.CloseEdition
  Set sketch3 = sketch
  wPart.Update
  Set toolCall1=sketch3
End Function

Function toolCall2(wpart,HybridBody1)
  wPart.InWorkObject = HybridBody1
  wPart.Update

  Set hypFact = wPart.HybridShapeFactory
  Set HybridShapePointCoord0 = hypFact.AddNewPointCoord(0, 0, 0)
  HybridBody1.AppendHybridShape HybridShapePointCoord0
  wPart.InWorkObject = HybridShapePointCoord0
  wPart.Update

  Set HybridShapePointCoord1 = hypFact.AddNewPointCoord(1, 0, 0)
  HybridBody1.AppendHybridShape HybridShapePointCoord1
  wPart.InWorkObject = HybridShapePointCoord1
  wPart.Update

  Set HybridShapePointCoord2 = hypFact.AddNewPointCoord(0, 1, 0)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  Set toolCall2=absref
End Function

Function toolCall3(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2

  Set startPoint = Factory2D.CreatePoint(0.75, 13.617543831396)
  Set endPoint = Factory2D.CreatePoint(0.75, 7.8)
  Set line = factory2d.CreateLine(0.75, 13.617543831396, 0.75, 7.8)
  line.StartPoint = startPoint
  line.EndPoint = endPoint

  Set startPoint = Factory2D.CreatePoint(0.75, 7.8)
  Set endPoint = Factory2D.CreatePoint(7.25, 7.8)
  Set line = factory2d.CreateLine(0.75, 7.8, 7.25, 7.8)
  line.StartPoint = startPoint
  line.EndPoint = endPoint

  Set startPoint = Factory2D.CreatePoint(7.25, 7.8)
  Set endPoint = Factory2D.CreatePoint(7.25, 13.617543831396)
  Set line = factory2d.CreateLine(7.25, 7.8, 7.25, 13.617543831396)
  line.StartPoint = startPoint
  line.EndPoint = endPoint

  Set startPoint = Factory2D.CreatePoint(7.25, 13.617543831396)
  Set endPoint = Factory2D.CreatePoint(0.75, 13.617543831396)
  Set cir = Factory2D.CreateCircle(4, -2.1316282072803e-14, 14, 1.3365161805512, 1.8050764730386)
  cir.StartPoint = startPoint
  cir.EndPoint = endPoint

  Set pk = Factory2D.CreatePoint(50, 0)
  Set pk = Factory2D.CreatePoint(-50, 0)
  Set line = Factory2d.CreateLine(50, 0, -50, 0)
  sketch.CenterLine = line

  wPart.Update

  Sketch.CloseEdition
  Set sketch5 = sketch
  wPart.Update
  Set toolCall3=sketch5
End Function

Function toolCall4(wpart,HybridBody1)
  wPart.InWorkObject = HybridBody1
  wPart.Update

  Set hypFact = wPart.HybridShapeFactory
  Set HybridShapePointCoord0 = hypFact.AddNewPointCoord(0, 0, 0)
  HybridBody1.AppendHybridShape HybridShapePointCoord0
  wPart.InWorkObject = HybridShapePointCoord0
  wPart.Update

  Set HybridShapePointCoord1 = hypFact.AddNewPointCoord(1, 0, 0)
  HybridBody1.AppendHybridShape HybridShapePointCoord1
  wPart.InWorkObject = HybridShapePointCoord1
  wPart.Update

  Set HybridShapePointCoord2 = hypFact.AddNewPointCoord(0, 1, 0)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  Set toolCall4=absref
End Function

Function toolCall5(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2

  Set startPoint = Factory2D.CreatePoint(4, -8.3)
  Set endPoint = Factory2D.CreatePoint(7.25, -8.3)
  Set line = factory2d.CreateLine(4, -8.3, 7.25, -8.3)
  line.StartPoint = startPoint
  line.EndPoint = endPoint

  Set startPoint = Factory2D.CreatePoint(7.25, -8.3)
  Set endPoint = Factory2D.CreatePoint(7.25, -11)
  Set line = factory2d.CreateLine(7.25, -8.3, 7.25, -11)
  line.StartPoint = startPoint
  line.EndPoint = endPoint

  Set startPoint = Factory2D.CreatePoint(7.25, -11)
  Set endPoint = Factory2D.CreatePoint(10.5, -13.7)
  Set line = factory2d.CreateLine(7.25, -11, 10.5, -13.7)
  line.StartPoint = startPoint
  line.EndPoint = endPoint

  Set startPoint = Factory2D.CreatePoint(10.5, -13.7)
  Set endPoint = Factory2D.CreatePoint(10.5, -36)
  Set line = factory2d.CreateLine(10.5, -13.7, 10.5, -36)
  line.StartPoint = startPoint
  line.EndPoint = endPoint

  Set startPoint = Factory2D.CreatePoint(10.5, -36)
  Set endPoint = Factory2D.CreatePoint(4, -36)
  Set line = factory2d.CreateLine(10.5, -36, 4, -36)
  line.StartPoint = startPoint
  line.EndPoint = endPoint

  Set startPoint = Factory2D.CreatePoint(4, -36)
  Set endPoint = Factory2D.CreatePoint(4, -8.3)
  Set line = factory2d.CreateLine(4, -36, 4, -8.3)
  line.StartPoint = startPoint
  line.EndPoint = endPoint

  Set pk = Factory2D.CreatePoint(4, -36)
  Set pk = Factory2D.CreatePoint(4, -8.3)
  Set line = Factory2d.CreateLine(4, -36, 4, -8.3)
  sketch.CenterLine = line

  wPart.Update

  Sketch.CloseEdition
  Set sketch7 = sketch
  wPart.Update
  Set toolCall5=sketch7
End Function

Function toolCall6(wpart,HybridBody1)
  wPart.InWorkObject = HybridBody1
  wPart.Update

  Set hypFact = wPart.HybridShapeFactory
  Set HybridShapePointCoord0 = hypFact.AddNewPointCoord(0, -36, 0)
  HybridBody1.AppendHybridShape HybridShapePointCoord0
  wPart.InWorkObject = HybridShapePointCoord0
  wPart.Update

  Set HybridShapePointCoord1 = hypFact.AddNewPointCoord(1, -36, 0)
  HybridBody1.AppendHybridShape HybridShapePointCoord1
  wPart.InWorkObject = HybridShapePointCoord1
  wPart.Update

  Set HybridShapePointCoord2 = hypFact.AddNewPointCoord(0, -36, -1)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  Set toolCall6=absref
End Function

Function toolCall7(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2

  Set startPoint = Factory2D.CreatePoint(-14.5, 6.5)
  Set endPoint = Factory2D.CreatePoint(-14.5, -6.5)
  Set line = factory2d.CreateLine(-14.5, 6.5, -14.5, -6.5)
  line.StartPoint = startPoint
  line.EndPoint = endPoint

  Set startPoint = Factory2D.CreatePoint(-14.5, -6.5)
  Set endPoint = Factory2D.CreatePoint(-1.5, -6.5)
  Set line = factory2d.CreateLine(-14.5, -6.5, -1.5, -6.5)
  line.StartPoint = startPoint
  line.EndPoint = endPoint

  Set startPoint = Factory2D.CreatePoint(-1.5, -6.5)
  Set endPoint = Factory2D.CreatePoint(-1.5, 6.5)
  Set line = factory2d.CreateLine(-1.5, -6.5, -1.5, 6.5)
  line.StartPoint = startPoint
  line.EndPoint = endPoint

  Set startPoint = Factory2D.CreatePoint(-1.5, 6.5)
  Set endPoint = Factory2D.CreatePoint(-14.5, 6.5)
  Set line = factory2d.CreateLine(-1.5, 6.5, -14.5, 6.5)
  line.StartPoint = startPoint
  line.EndPoint = endPoint

  wPart.Update

  Sketch.CloseEdition
  Set sketch10 = sketch
  wPart.Update
  Set toolCall7=sketch10
End Function

Function toolCall8(wpart,HybridBody1)
  wPart.InWorkObject = HybridBody1
  wPart.Update

  Set hypFact = wPart.HybridShapeFactory
  Set HybridShapePointCoord0 = hypFact.AddNewPointCoord(0, -36, 0)
  HybridBody1.AppendHybridShape HybridShapePointCoord0
  wPart.InWorkObject = HybridShapePointCoord0
  wPart.Update

  Set HybridShapePointCoord1 = hypFact.AddNewPointCoord(1, -36, 0)
  HybridBody1.AppendHybridShape HybridShapePointCoord1
  wPart.InWorkObject = HybridShapePointCoord1
  wPart.Update

  Set HybridShapePointCoord2 = hypFact.AddNewPointCoord(0, -36, -1)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  Set toolCall8=absref
End Function

Function toolCall9(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2

  Set startPoint = Factory2D.CreatePoint(9.5, 6.5)
  Set endPoint = Factory2D.CreatePoint(9.5, -6.5)
  Set line = factory2d.CreateLine(9.5, 6.5, 9.5, -6.5)
  line.StartPoint = startPoint
  line.EndPoint = endPoint

  Set startPoint = Factory2D.CreatePoint(9.5, -6.5)
  Set endPoint = Factory2D.CreatePoint(22.5, -6.5)
  Set line = factory2d.CreateLine(9.5, -6.5, 22.5, -6.5)
  line.StartPoint = startPoint
  line.EndPoint = endPoint

  Set startPoint = Factory2D.CreatePoint(22.5, -6.5)
  Set endPoint = Factory2D.CreatePoint(22.5, 6.5)
  Set line = factory2d.CreateLine(22.5, -6.5, 22.5, 6.5)
  line.StartPoint = startPoint
  line.EndPoint = endPoint

  Set startPoint = Factory2D.CreatePoint(22.5, 6.5)
  Set endPoint = Factory2D.CreatePoint(9.5, 6.5)
  Set line = factory2d.CreateLine(22.5, 6.5, 9.5, 6.5)
  line.StartPoint = startPoint
  line.EndPoint = endPoint

  wPart.Update

  Sketch.CloseEdition
  Set sketch12 = sketch
  wPart.Update
  Set toolCall9=sketch12
End Function

Function toolCall10(wpart,HybridBody1)
  wPart.InWorkObject = HybridBody1
  wPart.Update

  Set hypFact = wPart.HybridShapeFactory
  Set HybridShapePointCoord0 = hypFact.AddNewPointCoord(0, 0, 0)
  HybridBody1.AppendHybridShape HybridShapePointCoord0
  wPart.InWorkObject = HybridShapePointCoord0
  wPart.Update

  Set HybridShapePointCoord1 = hypFact.AddNewPointCoord(1, 0, 0)
  HybridBody1.AppendHybridShape HybridShapePointCoord1
  wPart.InWorkObject = HybridShapePointCoord1
  wPart.Update

  Set HybridShapePointCoord2 = hypFact.AddNewPointCoord(0, 0, -1)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  Set toolCall10=absref
End Function

Function toolCall11(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2

  Set pk = Factory2D.CreatePoint(4, 0)
  Set cir = Factory2D.CreateClosedCircle(4, 0, 20.3)

  Set pk = Factory2D.CreatePoint(4, 0)
  Set cir = Factory2D.CreateClosedCircle(4, 0, 12.5)

  wPart.Update

  Sketch.CloseEdition
  Set sketch14 = sketch
  wPart.Update
  Set toolCall11=sketch14
End Function

Function toolCall12(wpart,HybridBody1)
  wPart.InWorkObject = HybridBody1
  wPart.Update

  Set hypFact = wPart.HybridShapeFactory
  Set HybridShapePointCoord0 = hypFact.AddNewPointCoord(4, 0, 0)
  HybridBody1.AppendHybridShape HybridShapePointCoord0
  wPart.InWorkObject = HybridShapePointCoord0
  wPart.Update

  Set HybridShapePointCoord1 = hypFact.AddNewPointCoord(4, 0, -1)
  HybridBody1.AppendHybridShape HybridShapePointCoord1
  wPart.InWorkObject = HybridShapePointCoord1
  wPart.Update

  Set HybridShapePointCoord2 = hypFact.AddNewPointCoord(4, 1, 0)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  Set toolCall12=absref
End Function

Function toolCall13(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2

  Set startPoint = Factory2D.CreatePoint(-10.805367040463, -7.0098818193227)
  Set endPoint = Factory2D.CreatePoint(-4, -17.5)
  Set line = factory2d.CreateLine(-10.805367040463, -7.0098818193227, -4, -17.5)
  line.StartPoint = startPoint
  line.EndPoint = endPoint

  Set startPoint = Factory2D.CreatePoint(-4, -17.5)
  Set endPoint = Factory2D.CreatePoint(4, -17.5)
  Set line = factory2d.CreateLine(-4, -17.5, 4, -17.5)
  line.StartPoint = startPoint
  line.EndPoint = endPoint

  Set startPoint = Factory2D.CreatePoint(4, -17.5)
  Set endPoint = Factory2D.CreatePoint(10.805367040463, -7.0098818193227)
  Set line = factory2d.CreateLine(4, -17.5, 10.805367040463, -7.0098818193227)
  line.StartPoint = startPoint
  line.EndPoint = endPoint

  Set startPoint = Factory2D.CreatePoint(-10.805367040463, -7.0098818193227)
  Set endPoint = Factory2D.CreatePoint(10.805367040463, -7.0098818193227)
  Set cir = Factory2D.CreateCircle(-8.8817841970013e-16, 3.5527136788005e-15, 12.88, 3.7170821210739, 5.7076958396955)
  cir.StartPoint = startPoint
  cir.EndPoint = endPoint

  wPart.Update

  Sketch.CloseEdition
  Set sketch17 = sketch
  wPart.Update
  Set toolCall13=sketch17
End Function

Function toolCall14(wpart,HybridBody1)
  wPart.InWorkObject = HybridBody1
  wPart.Update

  Set hypFact = wPart.HybridShapeFactory
  Set HybridShapePointCoord0 = hypFact.AddNewPointCoord(0, 0, 0)
  HybridBody1.AppendHybridShape HybridShapePointCoord0
  wPart.InWorkObject = HybridShapePointCoord0
  wPart.Update

  Set HybridShapePointCoord1 = hypFact.AddNewPointCoord(1, 0, 0)
  HybridBody1.AppendHybridShape HybridShapePointCoord1
  wPart.InWorkObject = HybridShapePointCoord1
  wPart.Update

  Set HybridShapePointCoord2 = hypFact.AddNewPointCoord(0, 1, 0)
  HybridBody1.AppendHybridShape HybridShapePointCoord2
  wPart.InWorkObject = HybridShapePointCoord2
  wPart.Update

  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  wPart.InWorkObject = absPlane
  wPart.Update

  Set absRef = wPart.CreateReferenceFromGeometry(absPlane)
  wPart.Update

  Set toolCall14=absref
End Function

Function toolCall15(wpart,body,absref)
  wPart.InWorkObject = Body
  Set sketch = Body.Sketches.Add(absRef)
  wPart.InWorkObject = sketch
  wPart.Update

  Set factory2d = sketch.OpenEdition
  Set Axis2D7 = Sketch.AbsoluteAxis
  Set Line2D8 = Axis2D7.HorizontalReference
  Line2D8.ReportName = 1
  Set Line2D9 = Axis2D7.VerticalReference
  Line2D9.ReportName = 2

  Set startPoint = Factory2D.CreatePoint(4, -36)
  Set endPoint = Factory2D.CreatePoint(0, -36)
  Set line = factory2d.CreateLine(4, -36, 0, -36)
  line.StartPoint = startPoint
  line.EndPoint = endPoint

  Set startPoint = Factory2D.CreatePoint(0, -36)
  Set endPoint = Factory2D.CreatePoint(0.6765, -35.3235)
  Set line = factory2d.CreateLine(0, -36, 0.6765, -35.3235)
  line.StartPoint = startPoint
  line.EndPoint = endPoint

  Set startPoint = Factory2D.CreatePoint(0.6765, -35.3235)
  Set endPoint = Factory2D.CreatePoint(0.6765, -17.609422542893)
  Set line = factory2d.CreateLine(0.6765, -35.3235, 0.6765, -17.609422542893)
  line.StartPoint = startPoint
  line.EndPoint = endPoint

  Set startPoint = Factory2D.CreatePoint(0.6765, -17.609422542893)
  Set endPoint = Factory2D.CreatePoint(4, -15.690598923241)
  Set line = factory2d.CreateLine(0.6765, -17.609422542893, 4, -15.690598923241)
  line.StartPoint = startPoint
  line.EndPoint = endPoint

  Set startPoint = Factory2D.CreatePoint(4, -15.690598923241)
  Set endPoint = Factory2D.CreatePoint(4, -36)
  Set line = factory2d.CreateLine(4, -15.690598923241, 4, -36)
  line.StartPoint = startPoint
  line.EndPoint = endPoint

  Set pk = Factory2D.CreatePoint(4, -15.690598923241)
  Set pk = Factory2D.CreatePoint(4, -36)
  Set line = Factory2d.CreateLine(4, -15.690598923241, 4, -36)
  sketch.CenterLine = line

  wPart.Update

  Sketch.CloseEdition
  Set sketch19 = sketch
  wPart.Update
  Set toolCall15=sketch19
End Function

Sub CreatePart1
  On Error Resume Next

  Set SaveCaseDoc = CATIA.Documents.Item("SI_8_E.CATPart")

  If (Err.Number <> 0) Then
    ucaseName = GetUCaseName("SI_8_E.CATPart")
    Set SaveCaseDoc = CATIA.Documents.Item(ucaseName)
  End If

  Set PartDocument = SaveCaseDoc

  If (IsObject(PartDocument)) Then
    wPart.Activate
    Exit Sub
  End If

  Set fso = CreateObject("Scripting.FileSystemObject")

  If (fso.FileExists(storePath & "SI_8_E.CATPart")) Then
    CATIA.Documents.Open(storePath & "SI_8_E.CATPart")
    Set fso = Nothing
    Exit Sub
  ElseIf (fso.FileExists(storePath & GetUCaseName("SI_8_E.CATPart"))) Then
    CATIA.Documents.Open(storePath & GetUCaseName("SI_8_E.CATPart"))
    Set fso = Nothing
    Exit Sub
  End If

  Set fso = Nothing

  On Error Goto 0

  Set PartDocument = CATIA.Documents.Add("Part")
  Set unused1 = Partdocument.GetItem(1).UserRefProperties.CreateString("NN", "AHR_001_002")
  Set unused1 = Partdocument.GetItem(1).UserRefProperties.CreateString("NT", "Rod ends with a female thread")
  Set unused1 = Partdocument.GetItem(1).UserRefProperties.CreateString("NB", "SI 8 E")
  Set unused1 = Partdocument.GetItem(1).UserRefProperties.CreateString("NBSYN", "$DESIGNATION.")
  Set unused1 = Partdocument.GetItem(1).UserRefProperties.CreateString("LINA", "SI 8 E")
  Set unused1 = Partdocument.GetItem(1).UserRefProperties.CreateString("PRODUCTID", "208000002")
  Set unused1 = Partdocument.GetItem(1).UserRefProperties.CreateString("DESIGNATION", "SI 8 E")
  Set unused1 = Partdocument.GetItem(1).UserRefProperties.CreateString("DD", "8.000")
  Set unused1 = Partdocument.GetItem(1).UserRefProperties.CreateString("B", "8.000")
  Set unused1 = Partdocument.GetItem(1).UserRefProperties.CreateString("DDK", "13.000")
  Set unused1 = Partdocument.GetItem(1).UserRefProperties.CreateString("G", "M 8")
  Set unused1 = Partdocument.GetItem(1).UserRefProperties.CreateString("C1", "6.500")
  Set unused1 = Partdocument.GetItem(1).UserRefProperties.CreateString("DD2", "25.000")
  Set unused1 = Partdocument.GetItem(1).UserRefProperties.CreateString("DD4", "13.000")
  Set unused1 = Partdocument.GetItem(1).UserRefProperties.CreateString("HH1", "36.000")
  Set unused1 = Partdocument.GetItem(1).UserRefProperties.CreateString("LL3", "15.000")
  Set unused1 = Partdocument.GetItem(1).UserRefProperties.CreateString("LL4", "50.000")
  Set unused1 = Partdocument.GetItem(1).UserRefProperties.CreateString("LL5", "9.000")
  Set unused1 = Partdocument.GetItem(1).UserRefProperties.CreateString("LL7", "11.000")
  Set unused1 = Partdocument.GetItem(1).UserRefProperties.CreateString("R1", "0.300")
  Set unused1 = Partdocument.GetItem(1).UserRefProperties.CreateString("W", "11.000")
  Set unused1 = Partdocument.GetItem(1).UserRefProperties.CreateString("AT", "15.000")
  Set unused1 = Partdocument.GetItem(1).UserRefProperties.CreateString("LOAD1", "5.500")
  Set unused1 = Partdocument.GetItem(1).UserRefProperties.CreateString("LOAD2", "12.900")
  Set unused1 = Partdocument.GetItem(1).UserRefProperties.CreateString("TYPEID", "208000")
  Set unused1 = Partdocument.GetItem(1).UserRefProperties.CreateString("TAXONOMY", "1.000")
  Set unused1 = Partdocument.GetItem(1).UserRefProperties.CreateString("MALG", "8.000")
  Set unused1 = Partdocument.GetItem(1).UserRefProperties.CreateString("TPOLD", "1.250")
  Set unused1 = Partdocument.GetItem(1).UserRefProperties.CreateString("DESIGN", "rodend_fema1")
  Set unused1 = Partdocument.GetItem(1).UserRefProperties.CreateString("MAPPING", "BAZ50,DESIGNATION|IRD01,DD|IRL01,B|IRD20,DDK|HOT01,G|HOL01A,C1|HOD01A,DD2|HOD34,DD3|HOD35A,DD4|HOD35,DD4|HOL35,HH1|HOL50B,LL3|HOL40A,LL4|HOL21,LL5|HOL10B,LL7|IRR20,R1|HOL20,W|BCA10,AT|BCC02,LOAD1|HOC16,LOAD2|HOD35A,MASS|HOL61A,N|HOL60A,N1")
  Set unused1 = Partdocument.GetItem(1).UserRefProperties.CreateString("DESIGNLIST", "rodend_fema1,rodend_fema2x,rodend_fema2,rodend_fema3")
  Set unused1 = Partdocument.GetItem(1).UserRefProperties.CreateString("C1HELP", "6.175")
  Set unused1 = Partdocument.GetItem(1).UserRefProperties.CreateString("BR1", "0.000")
  Set unused1 = Partdocument.GetItem(1).UserRefProperties.CreateString("D3", "8.000")
  Set unused1 = Partdocument.GetItem(1).UserRefProperties.CreateString("BALG", "12.000")
  Set unused1 = Partdocument.GetItem(1).UserRefProperties.CreateString("C1ALG", "6.175")
  Set unused1 = Partdocument.GetItem(1).UserRefProperties.CreateString("SORT", "DD")
  Set unused1 = Partdocument.GetItem(1).UserRefProperties.CreateString("PIM", "SI 8 E")
  Set unused1 = Partdocument.GetItem(1).UserRefProperties.CreateString("TP", "1.250")
  Set unused1 = Partdocument.GetItem(1).UserRefProperties.CreateString("FAIL", "0.000")
  Set unused1 = Partdocument.GetItem(1).UserRefProperties.CreateString("VENDOR", "SKF")
  Set unused1 = Partdocument.GetItem(1).UserRefProperties.CreateString("SUPPLIER", "SKF")
  Set unused1 = Partdocument.GetItem(1).UserRefProperties.CreateString("ARTICLENO", "SI 8 E")
  Set unused1 = Partdocument.GetItem(1).UserRefProperties.CreateString("BOMINFO", "SI 8 E")
  Set unused1 = Partdocument.GetItem(1).UserRefProperties.CreateString("CREATOR", "CADENAS GmbH")
  Partdocument.GetItem(1).PartNumber = "SI 8 E-SI 8 E"
  Partdocument.GetItem(1).Definition = "Cadenas PARTsolutions"
  Partdocument.GetItem(1).DescriptionRef = "Rod ends with a female thread"

  set wpart=partDocument.Part
  Dim skCoord(8)
  Dim Body As AnyObject
  Set Body = wPart.MainBody
  Body.Name="SI 8 E"

  Dim HybridBody1 As HybridBody
  Set HybridBody1 = wPart.HybridBodies.Add
  HybridBody1.Name="SI 8 E Geo"

  Set absref=toolCall0(wpart,HybridBody1)
  Set sketch3=toolCall1(wpart,body,absref)
  wPart.InWorkObject = Body
  wPart.Update

  Set shaft = wPart.ShapeFactory.AddNewShaft(sketch3)
  shaft.firstAngle.value = 0
  shaft.SecondAngle.value = 360
  wPart.Update

  Set absref=toolCall2(wpart,HybridBody1)
  Set sketch5=toolCall3(wpart,body,absref)
  wPart.InWorkObject = Body
  wPart.Update

  Set shaft = wPart.ShapeFactory.AddNewShaft(sketch5)
  shaft.firstAngle.value = 0
  shaft.SecondAngle.value = 360
  wPart.Update

  Set absref=toolCall4(wpart,HybridBody1)
  Set sketch7=toolCall5(wpart,body,absref)
  wPart.InWorkObject = Body
  wPart.Update

  Set shaft = wPart.ShapeFactory.AddNewShaft(sketch7)
  shaft.firstAngle.value = 0
  shaft.SecondAngle.value = 360
  wPart.Update

  Set absref=toolCall6(wpart,HybridBody1)
  Set sketch10=toolCall7(wpart,body,absref)
  wPart.InWorkObject = Body
  wPart.Update

  Set pocket = wPart.ShapeFactory.AddNewPocket(sketch10, 9)
  pocket.IsSymmetric = True
  wPart.Update

  Set absref=toolCall8(wpart,HybridBody1)
  Set sketch12=toolCall9(wpart,body,absref)
  wPart.InWorkObject = Body
  wPart.Update

  Set pocket = wPart.ShapeFactory.AddNewPocket(sketch12, 9)
  pocket.IsSymmetric = True
  wPart.Update

  Set absref=toolCall10(wpart,HybridBody1)
  Set sketch14=toolCall11(wpart,body,absref)
  wPart.InWorkObject = Body
  wPart.Update

  Set pocket = wPart.ShapeFactory.AddNewPocket(sketch14, 15.6)
  pocket.IsSymmetric = True
  wPart.Update

  Set absref=toolCall12(wpart,HybridBody1)
  Set sketch17=toolCall13(wpart,body,absref)
  wPart.InWorkObject = Body
  wPart.Update

  Set pad = wPart.ShapeFactory.AddNewPad(sketch17, 3.25)
  pad.IsSymmetric = True
  wPart.Update

  Set absref=toolCall14(wpart,HybridBody1)
  Set sketch19=toolCall15(wpart,body,absref)
  wPart.InWorkObject = Body
  wPart.Update

  Set groove = wPart.ShapeFactory.AddNewGroove(sketch19)
  groove.FirstAngle.Value = 0
  groove.SecondAngle.Value = 360
  wPart.Update

  SaveDocument PartDocument, "SI_8_E.CATPart"
End Sub

Sub CreatePsolMain
  On Error Resume Next

  Set PartDocument = CATIA.Documents.Item("SI_8_E.CATPart")

  If (IsObject(PartDocument)) Then
    wPart.Activate
    Exit Sub
  End If

  If (IsEmpty(readSPath)) Then
    Exit Sub
  End If

  Set fso = CreateObject("Scripting.FileSystemObject")

  If (fso.FileExists(storePath & "SI_8_E.CATPart")) Then
    CATIA.Documents.Open(storePath & "SI_8_E.CATPart")
    Set fso = Nothing
    Exit Sub
  End If

  Set fso = Nothing

  On Error Goto 0

  CreatePart1


End Sub

CreatePsolMain
