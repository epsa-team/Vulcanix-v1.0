Attribute VB_Name = "Animation_mec"

Sub CATMain()
'----------------------------------------------------------------------------------------
'on récupère les variables de mesures qui nous intéressent
'pour cela on ouvre le doc
Dim AssyDoc As ProductDocument
Set AssyDoc = CATIA.ActiveDocument
'puis le product assemblage
Dim Assy As Product
Set Assy = AssyDoc.Product

'on récupère la liste de tous les paramètres de l'assemblage
Dim parameterList As Parameters
Set parameterList = Assy.Parameters

'maintenant on prend les paramètres qui nous intéressent grâce à leurs noms

Dim RearWheelTravel As parameter
Set RearWheelTravel = parameterList.Item("Rear Wheel travel\Gz")

Dim FrontWheelTravel As parameter
Set FrontWheelTravel = parameterList.Item("Front Wheel travel\Gz")

Dim SteeringAngle As parameter
Set SteeringAngle = parameterList.Item("Steering angle\Angle")

Dim FrontCamber As parameter
Set FrontCamber = parameterList.Item("Front camber\Angle")

Dim RearToe As parameter
Set RearToe = parameterList.Item("Rear Toe\Angle")

Dim RearCIR As parameter
Set RearCIR = parameterList.Item("Rear CIR\Gz")

Dim FrontCIR As parameter
Set FrontCIR = parameterList.Item("Front CIR\Gz")

'-----------------------------------------------------------------------------------------
'initialisation du excel
Dim objExcel As Object
Set objExcel = CreateObject("Excel.Application")
objExcel.Visible = True

objExcel.Workbooks.Add
LigneExcel = 0
'

Set objSheet = objExcel.ActiveWorkbook.Worksheets(1)
'
LigneExcel = LigneExcel + 1
objSheet.Cells(LigneExcel, 1) = "Commands"
objSheet.Cells(LigneExcel, 2) = "Rear Wheel Travel"
objSheet.Cells(LigneExcel, 3) = "Front Wheel Travel"
objSheet.Cells(LigneExcel, 4) = "Steering angle"
objSheet.Cells(LigneExcel, 5) = "Front Camber"
objSheet.Cells(LigneExcel, 6) = "Rear Toe"
objSheet.Cells(LigneExcel, 7) = "Rear CIR"
objSheet.Cells(LigneExcel, 8) = "Front CIR"
LigneExcel = LigneExcel + 1



'-----------------------------------------------------------------------------------------
' on va chercher le kinematics pour l'animer

Dim TheKinWorkbench As Workbench
Set TheKinWorkbench = CATIA.ActiveDocument.GetWorkbench("KinematicsWorkbench")
'on récup les mécanismes de kinematics
Dim TheMechanismsList As Mechanisms
Set TheMechanismsList = TheKinWorkbench.Mechanisms

'on récupère spécifiquement le mécanisme LAS
Dim LAS As Object
Set LAS = TheMechanismsList.Item(1)

'on l'affiche
intNbCommands = LAS.NbCommands - 1
ReDim varPosition(intNbCommands)
LAS.GetCommandValues varPosition
varPosition(3) = -30
varPosition(5) = -30
varPosition(8) = -30
varPosition(11) = -30

For intIndex = 1 To 11
        Assy.Update
        varPosition(3) = varPosition(3) + 5
        varPosition(5) = varPosition(5) + 5
        varPosition(8) = varPosition(8) + 5
        varPosition(11) = varPosition(11) + 5
        LAS.PutCommandValues varPosition
        objSheet.Cells(LigneExcel, 1) = varPosition
        objSheet.Cells(LigneExcel, 2) = RearWheelTravel.ValueAsString
        objSheet.Cells(LigneExcel, 3) = FrontWheelTravel.ValueAsString
        objSheet.Cells(LigneExcel, 4) = RearWheelTravel.ValueAsString
        objSheet.Cells(LigneExcel, 5) = FrontCamber.ValueAsString
        objSheet.Cells(LigneExcel, 6) = RearToe.ValueAsString
        objSheet.Cells(LigneExcel, 7) = RearCIR.ValueAsString
        objSheet.Cells(LigneExcel, 8) = FrontCIR.ValueAsString
        LigneExcel = LigneExcel + 1
        MsgBox varPosition(3)
Next

End Sub

Attribute VB_Name = "Bump"

Sub CATMain()
'----------------------------------------------------------------------------------------
'on récupère les variables de mesures qui nous intéressent
'pour cela on ouvre le doc
Dim AssyDoc As ProductDocument
Set AssyDoc = CATIA.ActiveDocument
'puis le product assemblage
Dim Assy As Product
Set Assy = AssyDoc.Product

'on récupère la liste de tous les paramètres de l'assemblage
Dim parameterList As Parameters
Set parameterList = Assy.Parameters

'maintenant on prend les paramètres qui nous intéressent grâce à leurs noms

Dim RearWheelTravel As parameter
Set RearWheelTravel = parameterList.Item("Rear Wheel travel\Gz")

Dim FrontWheelTravel As parameter
Set FrontWheelTravel = parameterList.Item("Front Wheel travel\Gz")

Dim RearSuspensionTravel As parameter
Set RearSuspensionTravel = parameterList.Item("Rear Suspension\Longueur")

Dim FrontSuspensionTravel As parameter
Set FrontSuspensionTravel = parameterList.Item("Front Suspension\Longueur")

Dim SteeringAngleRight As parameter
Set SteeringAngleRight = parameterList.Item("Right Wheel Angle\Angle")

Dim SteeringAngleLeft As parameter
Set SteeringAngleLeft = parameterList.Item("Left Wheel Angle\Angle")

Dim RearToe As parameter
Set RearToe = parameterList.Item("Rear Toe\Angle")

Dim FrontCamber As parameter
Set FrontCamber = parameterList.Item("Front Camber\Angle")

Dim RearCamber As parameter
Set RearCamber = parameterList.Item("Rear Camber\Angle")

Dim FrontCIRy As parameter
Set FrontCIRy = parameterList.Item("Front CIR\Diry")

Dim FrontCIRz As parameter
Set FrontCIRz = parameterList.Item("Front CIR\Dirz")

Dim RearCIRy As parameter
Set RearCIRy = parameterList.Item("Rear CIR\Diry")

Dim RearCIRz As parameter
Set RearCIRz = parameterList.Item("Rear CIR\Dirz")

'On récupère les paramètres de Commande
Dim Steering As parameter
Set Steering = parameterList.Item("Contraintes\Steering\Steering\Offset")

Dim Roll As parameter
Set Roll = parameterList.Item("Contraintes\Roll\Roll\Angle")

Dim Bump As parameter
Set Bump = parameterList.Item("Contraintes\Bump\Bump\Offset")

'-----------------------------------------------------------------------------------------
'initialisation du excel
Dim objExcel As Object
Set objExcel = CreateObject("Excel.Application")
objExcel.Visible = True

objExcel.Workbooks.Add
LigneExcel = 0
Set objSheet = objExcel.ActiveWorkbook.Worksheets(1)

LigneExcel = LigneExcel + 1
objSheet.Cells(LigneExcel, 1) = "Bump (mm)"
objSheet.Cells(LigneExcel, 2) = "Steering angle Right (deg)"
objSheet.Cells(LigneExcel, 3) = "Steering angle Left (deg)"
objSheet.Cells(LigneExcel, 4) = "Rear Toe (deg)"
objSheet.Cells(LigneExcel, 5) = "Front Wheel Travel (mm)"
objSheet.Cells(LigneExcel, 6) = "Rear Wheel Travel (mm)"
objSheet.Cells(LigneExcel, 7) = "Front Suspension Travel (mm)"
objSheet.Cells(LigneExcel, 8) = "Rear Suspension Travel (mm)"
objSheet.Cells(LigneExcel, 9) = "Front Camber(deg)"
objSheet.Cells(LigneExcel, 10) = "Rear Camber (deg)"
objSheet.Cells(LigneExcel, 11) = "Front CIR y (mm)"
objSheet.Cells(LigneExcel, 12) = "Front CIR z (mm)"
objSheet.Cells(LigneExcel, 13) = "Rear CIR y (mm)"
objSheet.Cells(LigneExcel, 14) = "Rear CIR z (mm)"
LigneExcel = LigneExcel + 1

Steering.ValuateFromString ("0mm")
Roll.ValuateFromString ("180deg")

pas = 1
valBump = -26 - pas
Do While valBump < 35
        valBump = valBump + pas
        Bump.ValuateFromString (valBump & "mm")
        'On Error Resume Next
        Assy.Update
        
        objSheet.Cells(LigneExcel, 1) = valBump
        objSheet.Cells(LigneExcel, 2) = SteeringAngleRight.ValueAsString
        objSheet.Cells(LigneExcel, 3) = SteeringAngleLeft.ValueAsString
        objSheet.Cells(LigneExcel, 4) = RearToe.ValueAsString
        objSheet.Cells(LigneExcel, 5) = FrontWheelTravel.ValueAsString
        objSheet.Cells(LigneExcel, 6) = RearWheelTravel.ValueAsString
        objSheet.Cells(LigneExcel, 7) = FrontSuspensionTravel.ValueAsString
        objSheet.Cells(LigneExcel, 8) = RearSuspensionTravel.ValueAsString
        objSheet.Cells(LigneExcel, 9) = FrontCamber.ValueAsString
        objSheet.Cells(LigneExcel, 10) = RearCamber.ValueAsString
        objSheet.Cells(LigneExcel, 11) = FrontCIRy.ValueAsString
        objSheet.Cells(LigneExcel, 12) = FrontCIRz.ValueAsString
        objSheet.Cells(LigneExcel, 13) = RearCIRy.ValueAsString
        objSheet.Cells(LigneExcel, 14) = RearCIRz.ValueAsString
        
        LigneExcel = LigneExcel + 1
Loop

End Sub

Attribute VB_Name = "Recup_mesures"
Sub CATMain()

Dim AssyDoc As ProductDocument
Set AssyDoc = CATIA.ActiveDocument

Dim Assy As Product
Set Assy = AssyDoc.Product

Dim parameterList As Parameters
Set parameterList = Assy.Parameters

Dim SteeringAngle As parameter
Set SteeringAngle = parameterList.Item("Steering angle\Angle")

MsgBox SteeringAngle.ValueAsString

End Sub

Attribute VB_Name = "Roll"

Sub CATMain()
'----------------------------------------------------------------------------------------
'on récupère les variables de mesures qui nous intéressent
'pour cela on ouvre le doc
Dim AssyDoc As ProductDocument
Set AssyDoc = CATIA.ActiveDocument
'puis le product assemblage
Dim Assy As Product
Set Assy = AssyDoc.Product

'on récupère la liste de tous les paramètres de l'assemblage
Dim parameterList As Parameters
Set parameterList = Assy.Parameters

'maintenant on prend les paramètres qui nous intéressent grâce à leurs noms

Dim RearWheelTravel As parameter
Set RearWheelTravel = parameterList.Item("Rear Wheel travel\Gz")

Dim FrontWheelTravel As parameter
Set FrontWheelTravel = parameterList.Item("Front Wheel travel\Gz")

Dim RearSuspensionTravel As parameter
Set RearSuspensionTravel = parameterList.Item("Rear Suspension\Longueur")

Dim FrontSuspensionTravel As parameter
Set FrontSuspensionTravel = parameterList.Item("Front Suspension\Longueur")

Dim SteeringAngleRight As parameter
Set SteeringAngleRight = parameterList.Item("Right Wheel Angle\Angle")

Dim SteeringAngleLeft As parameter
Set SteeringAngleLeft = parameterList.Item("Left Wheel Angle\Angle")

Dim RearToe As parameter
Set RearToe = parameterList.Item("Rear Toe\Angle")

Dim FrontCamber As parameter
Set FrontCamber = parameterList.Item("Front Camber\Angle")

Dim RearCamber As parameter
Set RearCamber = parameterList.Item("Rear Camber\Angle")

Dim FrontCIRy As parameter
Set FrontCIRy = parameterList.Item("Front CIR\Diry")

Dim FrontCIRz As parameter
Set FrontCIRz = parameterList.Item("Front CIR\Dirz")

Dim RearCIRy As parameter
Set RearCIRy = parameterList.Item("Rear CIR\Diry")

Dim RearCIRz As parameter
Set RearCIRz = parameterList.Item("Rear CIR\Dirz")

'On récupère les paramètres de Commande
Dim Steering As parameter
Set Steering = parameterList.Item("Contraintes\Steering\Steering\Offset")

Dim Roll As parameter
Set Roll = parameterList.Item("Contraintes\Roll\Roll\Angle")

Dim Bump As parameter
Set Bump = parameterList.Item("Contraintes\Bump\Bump\Offset")

'-----------------------------------------------------------------------------------------
'initialisation du excel
Dim objExcel As Object
Set objExcel = CreateObject("Excel.Application")
objExcel.Visible = True

objExcel.Workbooks.Add
LigneExcel = 0
Set objSheet = objExcel.ActiveWorkbook.Worksheets(1)

LigneExcel = LigneExcel + 1
objSheet.Cells(LigneExcel, 1) = "Roll (deg)"
objSheet.Cells(LigneExcel, 2) = "Steering angle Right (deg)"
objSheet.Cells(LigneExcel, 3) = "Steering angle Left (deg)"
objSheet.Cells(LigneExcel, 4) = "Rear Toe (deg)"
objSheet.Cells(LigneExcel, 5) = "Front Wheel Travel (mm)"
objSheet.Cells(LigneExcel, 6) = "Rear Wheel Travel (mm)"
objSheet.Cells(LigneExcel, 7) = "Front Suspension Travel (mm)"
objSheet.Cells(LigneExcel, 8) = "Rear Suspension Travel (mm)"
objSheet.Cells(LigneExcel, 9) = "Front Camber(deg)"
objSheet.Cells(LigneExcel, 10) = "Rear Camber (deg)"
objSheet.Cells(LigneExcel, 11) = "Front CIR y (mm)"
objSheet.Cells(LigneExcel, 12) = "Front CIR z (mm)"
objSheet.Cells(LigneExcel, 13) = "Rear CIR y (mm)"
objSheet.Cells(LigneExcel, 14) = "Rear CIR z (mm)"
LigneExcel = LigneExcel + 1

Steering.ValuateFromString ("0mm")
Bump.ValuateFromString ("0mm")

pas = 0.5
valRoll = 177 - pas
Do While valRoll < 183
        valRoll = valRoll + pas
        Roll.ValuateFromString (valRoll & "deg")
        'On Error Resume Next
        Assy.Update
        
        objSheet.Cells(LigneExcel, 1) = valRoll
        objSheet.Cells(LigneExcel, 2) = SteeringAngleRight.ValueAsString
        objSheet.Cells(LigneExcel, 3) = SteeringAngleLeft.ValueAsString
        objSheet.Cells(LigneExcel, 4) = RearToe.ValueAsString
        objSheet.Cells(LigneExcel, 5) = FrontWheelTravel.ValueAsString
        objSheet.Cells(LigneExcel, 6) = RearWheelTravel.ValueAsString
        objSheet.Cells(LigneExcel, 7) = FrontSuspensionTravel.ValueAsString
        objSheet.Cells(LigneExcel, 8) = RearSuspensionTravel.ValueAsString
        objSheet.Cells(LigneExcel, 9) = FrontCamber.ValueAsString
        objSheet.Cells(LigneExcel, 10) = RearCamber.ValueAsString
        objSheet.Cells(LigneExcel, 11) = FrontCIRy.ValueAsString
        objSheet.Cells(LigneExcel, 12) = FrontCIRz.ValueAsString
        objSheet.Cells(LigneExcel, 13) = RearCIRy.ValueAsString
        objSheet.Cells(LigneExcel, 14) = RearCIRz.ValueAsString
        
        LigneExcel = LigneExcel + 1
Loop

End Sub

Attribute VB_Name = "Steering"

Sub CATMain()
'----------------------------------------------------------------------------------------
'on récupère les variables de mesures qui nous intéressent
'pour cela on ouvre le doc
Dim AssyDoc As ProductDocument
Set AssyDoc = CATIA.ActiveDocument
'puis le product assemblage
Dim Assy As Product
Set Assy = AssyDoc.Product

'on récupère la liste de tous les paramètres de l'assemblage
Dim parameterList As Parameters
Set parameterList = Assy.Parameters

'maintenant on prend les paramètres qui nous intéressent grâce à leurs noms

Dim RearWheelTravel As parameter
Set RearWheelTravel = parameterList.Item("Rear Wheel travel\Gz")

Dim FrontWheelTravel As parameter
Set FrontWheelTravel = parameterList.Item("Front Wheel travel\Gz")

Dim RearSuspensionTravel As parameter
Set RearSuspensionTravel = parameterList.Item("Rear Suspension\Longueur")

Dim FrontSuspensionTravel As parameter
Set FrontSuspensionTravel = parameterList.Item("Front Suspension\Longueur")

Dim SteeringAngleRight As parameter
Set SteeringAngleRight = parameterList.Item("Right Wheel Angle\Angle")

Dim SteeringAngleLeft As parameter
Set SteeringAngleLeft = parameterList.Item("Left Wheel Angle\Angle")

Dim RearToe As parameter
Set RearToe = parameterList.Item("Rear Toe\Angle")

Dim FrontCamber As parameter
Set FrontCamber = parameterList.Item("Front Camber\Angle")

Dim RearCamber As parameter
Set RearCamber = parameterList.Item("Rear Camber\Angle")

Dim FrontCIRy As parameter
Set FrontCIRy = parameterList.Item("Front CIR\Diry")

Dim FrontCIRz As parameter
Set FrontCIRz = parameterList.Item("Front CIR\Dirz")

Dim RearCIRy As parameter
Set RearCIRy = parameterList.Item("Rear CIR\Diry")

Dim RearCIRz As parameter
Set RearCIRz = parameterList.Item("Rear CIR\Dirz")

'On récupère les paramètres de Commande
Dim Steering As parameter
Set Steering = parameterList.Item("Contraintes\Steering\Steering\Offset")

Dim Roll As parameter
Set Roll = parameterList.Item("Contraintes\Roll\Roll\Angle")

Dim Bump As parameter
Set Bump = parameterList.Item("Contraintes\Bump\Bump\Offset")

'-----------------------------------------------------------------------------------------
'initialisation du excel
Dim objExcel As Object
Set objExcel = CreateObject("Excel.Application")
objExcel.Visible = True

objExcel.Workbooks.Add
LigneExcel = 0
Set objSheet = objExcel.ActiveWorkbook.Worksheets(1)

LigneExcel = LigneExcel + 1
objSheet.Cells(LigneExcel, 1) = "Steering (mm)"
objSheet.Cells(LigneExcel, 2) = "Steering angle Right (deg)"
objSheet.Cells(LigneExcel, 3) = "Steering angle Left (deg)"
objSheet.Cells(LigneExcel, 4) = "Rear Toe (deg)"
objSheet.Cells(LigneExcel, 5) = "Front Wheel Travel (mm)"
objSheet.Cells(LigneExcel, 6) = "Rear Wheel Travel (mm)"
objSheet.Cells(LigneExcel, 7) = "Front Suspension Travel (mm)"
objSheet.Cells(LigneExcel, 8) = "Rear Suspension Travel (mm)"
objSheet.Cells(LigneExcel, 9) = "Front Camber(deg)"
objSheet.Cells(LigneExcel, 10) = "Rear Camber (deg)"
objSheet.Cells(LigneExcel, 11) = "Front CIR y (mm)"
objSheet.Cells(LigneExcel, 12) = "Front CIR z (mm)"
objSheet.Cells(LigneExcel, 13) = "Rear CIR y (mm)"
objSheet.Cells(LigneExcel, 14) = "Rear CIR z (mm)"
LigneExcel = LigneExcel + 1

Bump.ValuateFromString ("0mm")
Roll.ValuateFromString ("180deg")

pas = 1
valSteering = -25 - pas
Do While valSteering < 25
        valSteering = valSteering + pas
        Steering.ValuateFromString (valSteering & "mm")
        'On Error Resume Next
        Assy.Update
        
        objSheet.Cells(LigneExcel, 1) = valSteering
        objSheet.Cells(LigneExcel, 2) = SteeringAngleRight.ValueAsString
        objSheet.Cells(LigneExcel, 3) = SteeringAngleLeft.ValueAsString
        objSheet.Cells(LigneExcel, 4) = RearToe.ValueAsString
        objSheet.Cells(LigneExcel, 5) = FrontWheelTravel.ValueAsString
        objSheet.Cells(LigneExcel, 6) = RearWheelTravel.ValueAsString
        objSheet.Cells(LigneExcel, 7) = FrontSuspensionTravel.ValueAsString
        objSheet.Cells(LigneExcel, 8) = RearSuspensionTravel.ValueAsString
        objSheet.Cells(LigneExcel, 9) = FrontCamber.ValueAsString
        objSheet.Cells(LigneExcel, 10) = RearCamber.ValueAsString
        objSheet.Cells(LigneExcel, 11) = FrontCIRy.ValueAsString
        objSheet.Cells(LigneExcel, 12) = FrontCIRz.ValueAsString
        objSheet.Cells(LigneExcel, 13) = RearCIRy.ValueAsString
        objSheet.Cells(LigneExcel, 14) = RearCIRz.ValueAsString
        
        LigneExcel = LigneExcel + 1
Loop

End Sub
